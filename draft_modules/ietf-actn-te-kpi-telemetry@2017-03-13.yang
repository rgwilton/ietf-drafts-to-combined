module ietf-actn-te-kpi-telemetry {

    namespace
      "urn:ietf:params:xml:ns:yang:ietf-actn-te-kpi-telemetry";

    prefix "actn-tel";

    import ietf-actn-vn {
        prefix "actn-vn";
    }

    import ietf-te-kpi-telemetry {
        prefix "te-kpi";
    }

    organization
        "IETF Traffic Engineering Architecture and Signaling (TEAS)
        Working Group";

    contact
        "Editor: Young Lee <leeyoung@huawei.com>
         Editor: Dhruv Dhody <dhruv.ietf@gmail.com>
         Editor: Ricard Vilalta <ricard.vilalta@cttc.es>
         Editor: Satish Karunanithi <satish.karunanithi@gmail.com>";

    description
        "This module describes telemetry for actn vn model";

    revision 2017-03-13 {
        description
            "Initial revision. This YANG file defines
            the ACTN VN telemetry.";
        reference
            "Derived from earlier versions of base YANG files";
    }

    /*
     * Typedefs
     */

    typedef grouping-operation {
        type enumeration {
            enum MINIMUM {
                description
                    "Select the minimum param";
            }
            enum MAXIMUM {
                description
                    "Select the maximum param";
            }
            enum MEAN {
                description
                    "Select the MEAN of the params";
            }
            enum STD_DEV {
                description
                    "Select the standard deviation of the
                     monitored params";
            }
            enum SUM {
                description
                    "Select the sum of the monitored params";
                reference
                    "RFC 7823";
            }
            enum LOSS_PERCENT {
                description
                    "Select the packet loss percentage
                     calulation";
                reference
                    "RFC 7823";
            }
        }
        description
            "Operations to analize list of monitored params";
    }

    /*
     * Groupings
     */
    grouping vn-telemetry-param {
        description
            "telemetry-parameter for VN";
        uses te-kpi:telemetry-param;
    }

    grouping telemetry-grouping-op {
        description
            "Config how the VN telemetry should be applied";
        container grouping-op {
            description
                "The grouping operations";
            leaf delay-op {
                type grouping-operation;
                default MAXIMUM;
                description
                    "The operation that should be applied on the
                     VN-member telemetry to get the VN telemetry";
            }

            leaf delay-variation-op {
                type grouping-operation;
                default MAXIMUM;
                description
                    "The operation that should be applied on the
                     VN-member telemetry to get the VN telemetry";
            }

            leaf packet-loss-op {
                type grouping-operation;
                default MAXIMUM;
                description
                    "The operation that should be applied on the
                     VN-member telemetry to get the VN telemetry";
            }

            leaf utilized-bandwidth-op {
                type grouping-operation;
                default MAXIMUM;
                description
                    "The operation that should be applied on the
                     VN-member telemetry to get the VN telemetry";
            }
        }

    }

    /*
     * Augments
     */
    augment "/actn-vn:actn/actn-vn:vn/actn-vn:vn-list" {

        description
            "Augmentation parameters for state TE VN topologies.";

        container vn-telemetry {
          description
            "VN telemetry configurations";
            uses telemetry-grouping-op;
        }
        container vn-scaling-intent {
            description
                "scaling intent";
            uses te-kpi:scaling-intent;
        }
    }
    augment "/actn-vn:actn-state/actn-vn:vn/actn-vn:vn-list" {

        description
            "Augmentation parameters for state TE VN topologies.";

        container vn-telemetry {
            description
                "VN telemetry params";
            uses telemetry-grouping-op;
            uses vn-telemetry-param;
        }
        container vn-scaling-intent {
            description
                "scaling intent";
            uses te-kpi:scaling-intent;
        }
    }

    /*
     * VN-member augment
     */
    augment "/actn-vn:actn/actn-vn:vn/actn-vn:vn-list/" +
            "actn-vn:vn-member-list" {
        description
            "Augmentation parameters for state TE vn member
            topologies.";
        container vn-telemetry {
            description
                "VN Member config";
            uses telemetry-grouping-op;
        }
    }
    augment "/actn-vn:actn-state/actn-vn:vn/actn-vn:vn-list/" +
            "actn-vn:vn-member-list" {
        description
            "Augmentation parameters for state TE vn member
            topologies.";
        container vn-telemetry {
          description
            "VN telemetry params";
            uses telemetry-grouping-op;
          uses vn-telemetry-param;
        }
    }
}
