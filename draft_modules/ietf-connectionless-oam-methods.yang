module ietf-connectionless-oam-methods {
namespace "urn:ietf:params:xml:ns:yang:ietf-connectionless-oam-methods";
  prefix coam-methods;

  import ietf-interfaces {
    prefix if;
  }
  import ietf-connectionless-oam {
    prefix coam;
  }
  import ietf-yang-types {
    prefix yang;
  }

    organization "IETF LIME Working Group";
    contact
        "Deepak Kumar dekumar@cisco.com
         Qin Wu       bill.wu@huawei.com
         S Raghavan   srihari@cisco.com
         Zitao Wang   wangzitao@huawei.com
         R Rahman     rrahman@cisco.com";

    description
      "This YANG module defines the RPCs for ,
       connectionless OAM to be used within IETF
       in a protocol Independent manner.
       Functional level abstraction is indendent with
       YANG modeling. It is assumed that each protocol maps
       corresponding abstracts to its native format.
       Each protocol may extend the YANG model defined
       here to include protocol specific extensions";
    revision 2017-02-15 {
      description
        "02 version";
      reference
          "draft-ietf-lime-yang-connectionless-oam-methods";
    }

    rpc continuity-check {
      if-feature coam:continuity-check;
      description
        "Generates continuity-check as per RFC7276.";
      input {
        container destination-tp {
          uses coam:tp-address;
          description
            "Destination test point.";
        }
        uses coam:session-type;
        leaf source-interface {
          type if:interface-ref;
                  description
                  "Source interface.";
        }
        leaf outbound-interface {
          type if:interface-ref;

                  description
                  "Outbound interface.";
        }
        leaf count {
          type uint32;
          default "5";
          description
            "Specifies the number of
                        packets that will be sent.";
        }
        leaf vrf {
          type coam:routing-instance-ref;
          description
            "VRF instance.";
        }

        leaf ttl {
          type uint8;
          default "255";
          description
            "Time to live (TTL).";
        }
        leaf packet-size {
          type uint32 {
            range "64..10000";
          }
          default "64";
          description
            "Size of ping echo request
                        packets, in octets";
        }
      }
      output {
        list error-code-list {
          key "response-index";
          leaf response-index {
            type uint32;
            description
              "Response index.";
          }
          leaf status-code {
            type int32;
            description
              "Error code is ";
          }
          leaf status-sub-code {
            type uint8;
            description
              "Sub code.";
          }
          description
            "Error code list.";
        }

        uses coam:continuity-check-data;
      }
    }

    identity export-method {
      description
        "Base identity to represent a conceptual export-method.";
    }

    identity ipfix-export {
      base export-method;
      description
        "IPFIX based export. Configuration provided separately.";
    }

    identity yang-push-export {
      base export-method;
      description
          "Yang-push from draft-ietf-netconf-yang-push";
    }

    typedef export-method {
      type identityref {
        base export-method;
      }
      description
          "Export method type.";
    }

    typedef change-type {
      type enumeration {
        enum "create" {
        description
          "Change due to a create.";
        }
        enum "delete" {
        description
          "Change due to a delete.";
        }
        enum "modify" {
        description
          "Change due to an update.";
        }
      }
      description
        "Different types of changes that may occur.";
    }

    rpc cc-persistent-create {
      if-feature coam:continuity-check;
      description
        "Generates persistent continuity-check.";
      input {
        container destination-tp {
          uses coam:tp-address;
          description
            "Destination test point.";
        }

        uses coam:session-type;

        leaf source-interface {
          type if:interface-ref;
            description
                        "Source interface.";
        }

        leaf outbound-interface {
          type if:interface-ref;
            description
                        "Outbound interface.";
        }

        leaf vrf {
          type coam:routing-instance-ref;
          description
                  "VRF instance.";
        }

        leaf ttl {
          type uint8;
          default "255";
          description
            "Time to live (TTL).";
        }

        leaf data-export-method {
          type export-method;
          description
                  "Type of export.";
        }

        choice cc-trigger {
          description
            "Defines necessary conditions for
                        periodic or on-change trigger.";
          case periodic {
            description "Periodic reports.";
            leaf period {
              type yang:timeticks;
              description "Time interval between reports.";
            }
            leaf start-time {
              type yang:date-and-time;
              description
                          "Timestamp from which reports are started.";
            }
          }
          case on-change {
            description
                        "On-change trigger and not periodic.";
            leaf all-data-on-start {
              type boolean;
              description
                          "Full update needed on start or not.";
            }
            leaf-list excluded-change {
              type change-type;
              description
                          "Restrict which changes trigger an update.";
            }
          }
        }
      }
      output {
        list error-code-list {
          key "response-index";
          leaf response-index {
            type uint32;
            description
              "Response index.";
          }

          leaf status-code {
            type int32;
            description
              "Error code.";
          }

          leaf status-sub-code {
            type uint8;
            description
              "Sub code.";
          }

          description
            "Error code list.";
        }
        leaf cc-persistent-id {
          type string;
          description
                  "Id to act as a cookie.";
        }
      }
    }

    rpc cc-persistent-modify {
      if-feature coam:continuity-check;
      description
        "Modifies persistent continuity-check
                as per RFC7276.";
      input {
        leaf cc-persistent-id {
          type string;
          description
                  "Cookie Id to be used for modifications.";
        }

        leaf data-export-method {
          type export-method;
          description
                  "Type of export to use.";
        }

        choice cc-trigger {
          description
            "Defines necessary conditions for
                        periodic or on-change trigger.";
          case periodic {
            description "Periodic reports.";
            leaf period {
              type yang:timeticks;
              description
                          "Time interval between reports.";
            }
            leaf start-time {
              type yang:date-and-time;
              description
                          "Timestamp from which reports are started.";
            }
          }
          case on-change {
            description
                        "On-change trigger and not periodic.";
            leaf all-data-on-start {
              type boolean;
              description
                          "Full update needed on start or not.";
            }
            leaf-list excluded-change {
              type change-type;
              description
                          "Restrict which changes trigger an update.";
            }
          }
        }
      }
      output {
        list error-code-list {
          key "response-index";
          leaf response-index {
            type uint32;
            description
                        "Response index.";
          }

          leaf status-code {
            type int32;
            description
              "Error code";
          }

          leaf status-sub-code {
            type uint8;
            description
              "Sub code.";
          }

          description
            "Error code list.";
        }

        leaf cc-persistent-id {
          type string;
          description
                  "Id to represent a cookie.";
        }
      }
    }

    rpc cc-persistent-delete {
      if-feature coam:continuity-check;
      description
        "Deletes persistent continuity-check as per RFC7276.";
      input {
        leaf cc-persistent-id {
          type string;
          description
                  "Cookie Id to be used in deletion.";
        }
      }
      output {
        list error-code-list {
          key "response-index";
          leaf response-index {
            type uint32;
            description
                        "Response index.";
          }

          leaf status-code {
            type int32;
            description
              "Error code.";
          }

          leaf status-sub-code {
            type uint8;
            description
                        "Sub code.";
          }

          description
            "Error code list.";
        }
      }
    }

    rpc path-discovery {
      description
        "Generates path discovery as per RFC7276.";
      input {
        container destination-tp {
          uses coam:tp-address;
          description
          "Destination test point.";

        }
        uses coam:session-type;
        leaf source-interface {
          type if:interface-ref;
          description
            "Source interface.";
        }

        leaf outbound-interface {
          type if:interface-ref;
          description
            "Outbound interface.";
        }

        leaf vrf {
          type coam:routing-instance-ref;
          description
            "VRF";
        }

        leaf max-ttl {
          type uint8;
          default "255";
          description
            "Max ttl.";
        }
      }
      output {
        list response-list {
          key "response-index";
          description
            "Path discovery response list.";
          leaf response-index {
            type uint32;
            description
              "Response index.";
          }

          leaf status-code {
            type int32;
            description
              "Error code is ";
          }

          leaf status-sub-code {
            type uint8;
            description
              "Sub code is ";
          }
        }

        uses coam:path-discovery-data;

       }
    }

    rpc pd-persistent-create {
      description
        "Generates persistent path discovery.";
      input {
        container destination-tp {
          uses coam:tp-address;
          description
            "Destination test point.";

        }

        uses coam:session-type;

        leaf source-interface {
          type if:interface-ref;
          description
            "Source interface.";
        }

        leaf outbound-interface {
          type if:interface-ref;
          description
            "Outbound interface.";
        }

        leaf vrf {
          type coam:routing-instance-ref;
          description
            "VRF";
        }

        leaf max-ttl {
          type uint8;
          default "255";
          description
            "Max ttl.";
        }
        leaf data-export-method {
          type export-method;
          description
                  "Type of export.";
        }

        choice pd-trigger {
          description
            "Defines necessary conditions
                        for periodic or on-change
             trigger.";
          case periodic {
            description
                        "Periodic reports.";
            leaf period {
              type yang:timeticks;
              description
                          "Time interval between reports.";
            }
            leaf start-time {
              type yang:date-and-time;
              description
                          "Timestamp from which reports are started.";
            }
          }
          case on-change {
            description
                        "On-change trigger and not periodic.";
            leaf all-data-on-start {
              type boolean;
              description
                          "Full update needed on start or not.";
            }
            leaf-list excluded-change {
              type change-type;
              description
                          "Restrict which changes trigger an update.";
            }
          }
        }
      }
      output {
        list response-list {
          key "response-index";
          description
            "Path discovery response list.";
          leaf response-index {
            type uint32;
            description
            "Response index.";
          }

          leaf status-code {
            type int32;
            description
            "Error code is ";
          }

          leaf status-sub-code {
            type uint8;
            description
            "Sub code is ";
          }

          leaf pd-persistent-id {
            type string;
            description
                        "Id to act as a cookie.";
          }
        }
      }
    }

    rpc pd-persistent-modify {
      description
        "Modifies persistent path discovery.";
      input {
        leaf pd-persistent-id {
          type string;
          description "Cookie Id to be used for modifications.";
        }

        leaf data-export-method {
          type export-method;
          description "Type of export.";
        }

        choice pd-trigger {
          description
            "Defines necessary conditions for periodic or on-change
             trigger.";
          case periodic {
            description "Periodic reports.";
            leaf period {
              type yang:timeticks;
              description
                          "Time interval between reports.";
            }
            leaf start-time {
              type yang:date-and-time;
              description
                          "Timestamp from which reports are started.";
            }
          }
          case on-change {
            description
                        "On-change trigger and not periodic.";
            leaf all-data-on-start {
              type boolean;
              description
                          "Full update needed on start or not.";
            }
            leaf-list excluded-change {
              type change-type;
              description
                          "Restrict which changes trigger an update.";
            }
          }
        }
      }
      output {
        list response-list {
          key "response-index";
          description
            "path discovery response list.";
          leaf response-index {
            type uint32;
            description
              "response index.";
          }

          leaf status-code {
            type int32;
            description
              "error code is ";
          }

          leaf status-sub-code {
            type uint8;
            description
              "sub code is ";
          }

          leaf pd-persistent-id {
            type string;
            description "Id to act as a cookie.";
          }
        }
      }
    }

    rpc pd-persistent-delete  {
      description
        "Deletes persistent path discovery.";
      input {
        leaf pd-persistent-id {
          type string;
          description "Cookie Id to be used in deletion.";
        }
      }

      output {
        list response-list {
          key "response-index";
          description
            "path discovery response list.";
          leaf response-index {
            type uint32;
            description
              "response index.";
          }

          leaf status-code {
            type int32;
            description
              "error code is ";
          }

          leaf status-sub-code {
            type uint8;
            description
              "sub code is ";
          }
        }
      }
    }
}
