module ietf-diffserv {
  yang-version 1;
  namespace "urn:ietf:params:xml:ns:yang:ietf-diffserv";
  prefix diffserv;
  import ietf-interfaces {
    prefix if;
  }
  import ietf-qos-classifier {
    prefix classifier;
  }
  import ietf-qos-policy {
    prefix policy;
  }
  import ietf-qos-action {
    prefix action;
  }
  import ietf-qos-target {
    prefix target;
  }
  organization "IETF RTG (Routing Area) Working Group";
  contact
    "WG Web:   <http://tools.ietf.org/wg/rtgwg/>
     WG List:  <mailto:rtgwg@ietf.org>
     WG Chair: Chris Bowers
               <mailto:cbowers@juniper.net>
     WG Chair: Jeff Tantsura
               <mailto:jefftant.ietf@gmail.com>
     Editor:   Aseem Choudhary
               <mailto:asechoud@cisco.com>
     Editor:   Mahesh Jethanandani
               <mailto:mjethanandani@gmail.com
     Editor:   Norm Strahle
               <mailto:nstrahle@juniper.net>";
  description
    "This module contains a collection of YANG definitions for
     configuring diffserv specification implementations.
     Copyright (c) 2014 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC XXXX; see
     the RFC itself for full legal notices.";
  revision 2016-06-15 {
    description
      "Latest revision of diffserv based classifier";
    reference "RFC XXXX";
  }
  augment "/classifier:classifiers/classifier:classifier-entry/" +
          "classifier:filter-entry" {
    choice filter-param {
      description
        "Choice of filter types";
      case dscp {
        uses classifier:dscp-cfg;
        description
          "Filter containing list of dscp ranges";
      }
      case source-ip-address {
        uses classifier:source-ip-address-cfg;
        description
          "Filter containing list of source ip addresses";
      }
      case destination-ip-address {
        uses classifier:destination-ip-address-cfg;
        description
          "Filter containing list of destination ip address";
      }
      case source-port {
        uses classifier:source-port-cfg;
        description
          "Filter containing list of source-port ranges";
      }
      case destination-port {
        uses classifier:destination-port-cfg;
        description
          "Filter containing list of destination-port ranges";
      }
      case protocol {
        uses classifier:protocol-cfg;
        description
          "Filter Type Protocol";
      }
    }
    description
      "augments diffserv filters to qos classifier";
  }

 augment "/policy:policies" +
         "/policy:policy-entry" +
         "/policy:classifier-entry" +
         "/policy:filter-entry" {
   choice filter-params {
     description
       "Choice of action types";
     case dscp {
       uses classifier:dscp-cfg;
         description
           "Filter containing list of dscp ranges";
     }
     case source-ip-address {
       uses classifier:source-ip-address-cfg;
       description
         "Filter containing list of source ip addresses";
     }
     case destination-ip-address {
       uses classifier:destination-ip-address-cfg;
       description
         "Filter containing list of destination ip address";
     }
     case source-port {
       uses classifier:source-port-cfg;
       description
         "Filter containing list of source-port ranges";
     }
     case destination-port {
       uses classifier:destination-port-cfg;
       description
         "Filter containing list of destination-port ranges";
     }
     case protocol {
       uses classifier:protocol-cfg;
       description
         "Filter Type Protocol";
     }
   }
   description
     "Augments Diffserv Classifier with common filter types";
 }
 augment "/policy:policies/policy:policy-entry/" +
          "policy:classifier-entry/" +
          "policy:classifier-action-entry-cfg" {
    choice action-cfg-params {
      description
        "Choice of action types";
      case dscp-marking {
        uses action:dscp-marking;
      }
    }
    description
      "augments dscp-marking and meter to qos policy";
  }
  augment "/if:interfaces/if:interface/target:qos-target-entry/" +
          "target:qos-target-classifier-statistics" {
    container diffserv-action-statistics {
      uses target:meter-stats;
      description
        "meter statistics";
    }
    description
      "augments meter stats to qos target module";
  }
}
