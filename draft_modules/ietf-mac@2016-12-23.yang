module ietf-mac {
  namespace "http://www.huawei.com/netconf/vrp/huawei-mac";
  prefix mac;

    import ietf-inet-types {
         prefix "inet";
       }
    import ietf-yang-types {
      prefix yang;
    }

  organization
    "Huawei Technologies Co.,Ltd.";
  contact
    "Huawei Industrial Base Bantian, Longgang Shenzhen 518129
      People's Republic of China
      Website: http://www.huawei.com Email: support@huawei.com";
  description
    "MAC address forwarding.";

  revision 2016-12-30 {
    description
      "Init revision";
    reference "Huawei private.";
  }

  typedef macVlanId {
    type uint16 {
      range "1..4094";
    }
      description
      "VLAN Id.";
  }

  typedef macType {
    type enumeration {
      enum "static" {

        value 0;
        description
          "Static MAC address entry.";
      }
      enum "dynamic" {
        value 1; 
        description
          "Dynamic MAC address entry.";
      }
      enum "blackHole" {
        value 2;
        description
          "Blackhole MAC address entry";
      }
      enum "sticky" {
        value 3;
        description
          "sticky MAC address entry";
      }
    }
    description
    "MAC address type.";
  }

  typedef limitType {
    type enumeration {
      enum "macLimit" {
        value 0;
        description
          "Interface MAC rule limit.";
      }
      enum "macApply" {
        value 1;
        description
          "Interface MAC rule application.";
      }
    }
    description
    "MAC address limit type.";
  }
    typedef macLimitForward {
    type enumeration {
      enum "forward" {
        value 0;
        description
          "Forward.";
      }
      enum "discard" {
        value 1;
        description
          "Discard.";

      }
    }
    description
    "MAC address limit forward type.";
  }

  typedef macEnableStatus {
    type enumeration {
      enum "enable" {
        value 0;
        description
          "Enable.";
      }
      enum "disable" {
        value 1;
        description
          "Disable.";
      }
    }
    description
    "MAC enable type.";
  }

    typedef macOutIfType {
    type enumeration {
      enum "ac" {
        value 0;
        description
          "AC.";
      }
      enum "pw" {
        value 1;
        description
          "PW.";
      }
    }
    description
    "MAC out if type.";
  }

  typedef macPwEncapType {
    type enumeration {
      enum "ethernet" {
        value 0;
        description
          "Ethernet.";
      }
      enum "vlan" {
        value 1;
        description
          "VLAN.";
      }
    }
    description
    "MAC encapsulation type.";
  }

  typedef directionType {
    type enumeration {
      enum "inbound" {
        value 0;
        description
          "Inbound.";
      }
      enum "outbound" {
        value 1;
        description
          "Outbound.";
      }
    }
    description
    "Direction type.";	
  }

  typedef discardType {
    type enumeration {
      enum "broadcastDiscard" {
        value 0;
        description
          "Discard broadcast.";
      }
      enum "unknownMulticastDiscard" {
        value 1;
        description
          "Discard unknown multicast.";
      }
      enum "unknownUnicastDiscard" {
        value 2;
        description
          "Discard Unknown unicast.";
      }
    }
    description
    "Discard type.";	
  }

    typedef broadcastDomainType {
    type enumeration {
      enum "VLAN" {
        value 0;
        description
          "VLAN Type.";
      }
      enum "VSI" {
        value 1;
        description
          "VSI Type.";
      }
      enum "BD" {

        value 2;
        description
          "BD Type.";
      }
    }
    description
    "Domain type.";	
  }

    typedef macAgeTimeType {
    type enumeration {
      enum "enable" {
        value 0;
        description
          "Enable MAC address global aging.";
      }
      enum "disable" {
        value 1;
        description
          "Disable MAC address global aging.";
      }
    }
    description
    "MAC address age time type.";
  }

  container mac {
    description
      "MAC address forwarding. ";
    container globalAttribute {
      description
        "MAC global attribute.";
      leaf macAgeTimeEnable {
        type macAgeTimeType;
        default "enable";
        description
          "Whether MAC address aging is enabled.";

      }
      leaf macAgingTime {
        when "not(../macAgeTimeEnable='disable') or 
             ../macAgeTimeEnable='enable'";
        type uint32 {
          range "60..1000000";
        }
        default "300";
        description
          "Aging time.";
      }
    }
    container vlanFdbs {
      description
        "VLAN forwarding table.";
      list vlanFdb {
        key "macAddress vlanId slotId";
        description
          "VLAN forwarding entry.";
        leaf macAddress {
          type yang:mac-address;
          description
            "MAC address in the format of H-H-H.";
        }
        leaf vlanId {
          type macVlanId;
          description
            "VLAN ID.";
        }
        leaf slotId {
          type string {
            length "1..24";
          }
          description
            "Slot ID.";
        }
        leaf macType {
          type macType;
          must "((../macType='static' or ../macType='blackHole') )";
          mandatory true;
          description
            "MAC address type, such as blackhole, static, and dynamic.";
        }
        leaf outIfName {
          when "not(../macType='blackHole') or ../macType='static'";
              type string;
              description
                "Outbound interface name.";

        }
        leaf outNickname {
          type string {
            length "1..31";
          }
          config false;
          mandatory true;
          description
            "Nickname.";
        }
        leaf isCeDefault {
          when "not(../macType='blackHole')";
          type boolean;
          default "false";
          description
            "CE default VLAN.";
        }
        leaf ceVlanId {
          when "not(../macType='blackHole') or ../isCeDefault='false' 
               and ../macType='static'";
          type macVlanId;
          description
            "User VLAN ID.";
        }
        leaf isFlood {
          type boolean;
          default "false";
          description
            "Flooding MAC.";
        }
        leaf isIMac {
          type boolean;
          default "false";
          description
            "Ingress MAC.";
        }
        leaf learnedPeriod {
          type uint32 {
            range "0..4294967294";
          }
          default "0";
          config false;
          description
            "Dynamic MAC Holding Time.";
        }
        container outPeerIPs {
          description
            "Out Peer IPs.";

          list outPeerIP {
            key "outPeerIP";
            config false;
            description
              "Out Peer IP.";
            leaf outPeerIP {
              type inet:ip-address;
              description
                "Out Peer IP.";
            }
          }
        }
      }
    }
    container vsiFdbs {
      description
        "VSI forwarding table.";
      list vsiFdb {
        key "vsiName slotId vlanid macAddress";
        description
          "VSI Forwarding entry.";
        leaf vsiName {
          type string {
            length "1..31";
          }
          description
            "VSI Name.";
        }
        leaf slotId {
          type string {
            length "1..24";
          }
          description
            "Slot ID.";
        }
        leaf vlanid {
          type uint16 {
            range "0..4094";
          }
          description
            "VLAN ID.";
        }
        leaf vlanifName {
          when "not(../outIfType='pw' or ../macType='blackHole') 
               or ../outIfType='ac' and ../macType='static'";
          type string;

          description
            "VLANIF interface.";
        }
        leaf pevid {
          when "not(../outIfType='pw' or ../macType='blackHole') 
                or ../outIfType='ac' and ../macType='static'";
          type macVlanId;
          description
            "Outer VLAN tag.";
        }
        leaf cevid {
          when "not(../outIfType='pw' or ../macType='blackHole') 
                or ../outIfType='ac' and ../macType='static'";
          type macVlanId;
          description
            "Inner VLAN tag.";
        }
        leaf macAddress {
          type yang:mac-address;
          description
            "MAC address in the format of H-H-H.";
        }
        leaf macType {
          type macType;
          must "((../macType='static' or ../macType='blackHole') )";
          mandatory true;
          description
            "MAC Type of an interface.";
        }
        leaf outIfType {
          when "not(../macType='blackHole') or ../macType='static'";
          type macOutIfType;
          mandatory true;
          description
            "Outbound interface type.";
        }
        leaf outIfName {
          when "not(../outIfType='pw' or ../macType='blackHole' 
               or ../outIfType='pw' and ../macType='static') 
               or ../outIfType='ac' and ../macType='static'";
          type string;
          mandatory true;
          description
            "Outbound interface name.";
        }
        leaf pwId {
          when "not(../macType='blackHole' or ../outIfType='ac' 
                and ../macType='static') or ../outIfType='pw' 
                and ../macType='static'";
          type uint32 {
            range "1..4294967295";
          }

          description
            "PW ID.";
        }
        leaf pwEncap {
          when "not(../macType='blackHole' or ../outIfType='ac' 
                and ../macType='static') or ../outIfType='pw' 
                and ../macType='static'";
          type macPwEncapType;
          mandatory true;
          description
            "PW encapsulation type.";
        }
        leaf peerIp {
          when "not(../macType='blackHole' or ../outIfType='ac' 
                and ../macType='static') or ../outIfType='pw' 
                and ../macType='static'";
          type inet:ip-address;
          description
            "Peer IP address.";
        }
        leaf pwName {
          type string {
            length "1..31";
          }
          description
            "PW Name.";
        }
        leaf isIMac {
          type boolean;
          mandatory true;
          description
            "Ingress MAC.";
        }
        leaf learnedPeriod {
          type uint32 {
            range "0..4294967294";
          }
          default "0";
          config false;
          description
            "Dynamic MAC Holding Time.";
        }
      }
    }
    container vsiFdbDynamics {
      description
        "VSI Forwarding Table on Slot.";

      list vsiFdbDynamic {
        key "vsiName slotId vlanid macAddress outIfName";
        config false;
        description
          "VSI Forwarding Table on Slot.";
        leaf vsiName {
          type string {
            length "1..31";
          }
          description
            "VSI Name.";
        }
        leaf slotId {
          type string {
            length "1..24";
          }
          description
            "Slot ID.";
        }
        leaf vlanid {
          type uint16 {
            range "0..4094";
          }
          description
            "VLAN ID.";
        }
        leaf vlanifName {
          type string;
          description
            "VLANIF interface.";
        }
        leaf pevid {
          type macVlanId;
          description
            "Outer VLAN tag.";
        }
        leaf cevid {
          type macVlanId;
          description
            "Inner VLAN tag.";
        }
        leaf macAddress {
          type yang:mac-address;
          description
            "MAC address in the format of H-H-H.";
        }
        leaf macType {
          type macType;

          mandatory true;
          description
            "MAC Type of an interface.";
        }
        leaf outIfType {
          type macOutIfType;
          mandatory true;
          description
            "Outbound interface type.";
        }
        leaf outIfName {
          type string;
          description
            "Outbound interface name.";
        }
        leaf pwId {
          type uint32 {
            range "1..4294967295";
          }
          description
            "PW ID.";
        }
        leaf pwEncap {
          type macPwEncapType;
          mandatory true;
          description
            "PW encapsulation type.";
        }
        leaf peerIp {
          type inet:ip-address;
          mandatory true;
          description
            "Peer IP address.";
        }
        leaf pwName {
          type string {
            length "1..31";
          }
          description
            "PW Name.";
        }
        leaf isIMac {

          type boolean;
          mandatory true;
          description
            "Ingress MAC.";
        }
      }
    }
    container bdFdbs {
      description
        "BD forwarding entries.";
      list bdFdb {
        key "slotId macAddress bdId";
        description
          "BD forwarding entry.";
        leaf slotId {
          type string {
            length "1..50";
          }
          description
            "Slot number.";
        }
        leaf macAddress {
          type yang:mac-address;
          description
            "MAC address of a bridge domain.";
        }
        leaf bdId {
          type uint32 {
            range "1..16777215";
          }
          description
            "ID of a bridge domain.";
        }
        leaf macType {
          type macType;
          must "((../macType='static' or ../macType='blackHole') )";
          mandatory true;
          description
            "MAC address type of a bridge domain.";
        }
        leaf outIfName {
          when "not(../macType='blackHole') or ../unTag='false' 
                    and ../peDefault='false' and ../ceDefault='false' 
                    and ../macType='static'";
          type string;
          mandatory true;
          description
            "Outbound interface name.";
        }

        leaf unTag {
          when "not(../macType='blackHole') or ../unTag='false' 
                and ../peDefault='false' and ../ceDefault='false' 
                and ../macType='static'";
          type boolean;
          default "false";
          description
            "Packets without VLAN tags.";
        }
        leaf peDefault {
          when "not(../macType='blackHole' or ../unTag='true') 
               or ../unTag='false' and ../peDefault='false' 
               and ../ceDefault='false' and ../macType='static'";
          type boolean;
          default "false";
          description
            "PE default VLAN.";
        }
        leaf ceDefault {
          when "not(../peDefault='true' or ../macType='blackHole' 
                or ../unTag='true') or ../unTag='false' 
                and ../peDefault='false' and ../ceDefault='false' 
                and ../macType='static'";
          type boolean;
          default "false";
          description
            "CE default VLAN.";
        }
        leaf vid {
          when "not(../peDefault='true' or ../macType='blackHole' 
                or ../unTag='true') or ../unTag='false' 
                and ../peDefault='false' and ../ceDefault='false' 
                and ../macType='static'";
          type macVlanId;
          description
            "Outer VLAN tag.";
        }
        leaf cevid {
          when "not(../peDefault='true' or ../ceDefault='true' 
                or ../macType='blackHole' or ../unTag='true') 
                or ../unTag='false' and ../peDefault='false' 
                and ../ceDefault='false' and ../macType='static'";
          type macVlanId;
          description
            "Inner VLAN tag.";
        }
        leaf learnedPeriod {
          type uint32 {
            range "0..4294967294";
          }
          default "0";
          config false;
          description
            "Dynamic MAC Holding Time.";
        }
      }
    }
    container macLimitRules {
      description
        "Global MAC address learning limit rule.";
      list macLimitRule {

        key "ruleName";
        description
          "Global MAC address learning limit.";
        leaf ruleName {
          type string {
            length "1..31";
          }
          description
            "Global MAC address learning limit rule name.";
        }
        leaf maximum {
          type uint32 {
            range "0..131072";
          }
          must "not(../rate=0) or (../rate=0 and ../maximum>0)";
          mandatory true;
          description
            "Maximum number of MAC addresses that can be learned.";
        }
        leaf rate {
          type uint16 {
            range "0..1000";
          }
          must "not(../maximum=0) or (../maximum=0 and ../rate>0)";
          default "0";
          description
            "Interval at which MAC addresses are learned.";
        }
        leaf action {
          type macLimitForward;
          default "discard";
          description
            "Discard or forward after the number of learned MAC 
             addresses reaches the maximum number.";
        }
        leaf alarm {
          type macEnableStatus;
          default "enable";
          description
            "Whether an alarm is generated after the number of 
             learned MAC addresses reaches the maximum number.";
        }
      }
    }
    container vlanMacLimits {
      description
        "VLAN MAC address limit list.";
      list vlanMacLimit {
        key "vlanId";
        description

          "VLAN MAC address limit.";
        leaf vlanId {
          type macVlanId;
          description
            "VLAN ID.";
        }
        leaf maximum {
          type uint32 {
            range "0..130048";
          }
          must "not(../rate=0) or (../rate=0 and ../maximum>0)";
          mandatory true;
          description
            "Maximum number of MAC addresses that can be learned 
             in a VLAN.";
        }
        leaf rate {
          type uint16 {
            range "0..1000";
          }
          must "not(../maximum=0) or (../maximum=0 and ../rate>0)";
          default "0";
          description
            "Interval at which MAC addresses are learned in a VLAN.";
        }
        leaf action {
          type macLimitForward;
          default "discard";
          description
            "Discard or forward after the number of learned MAC 
             addresses reaches the maximum number in a VLAN.";
        }
        leaf alarm {
          type macEnableStatus;
          default "enable";
          description
            "Whether an alarm is generated after the number of learned 
             MAC addresses reaches the maximum number in a VLAN.";
        }
      }
    }
    container vsiMacLimits {
      description
        "VSI MAC address limit list.";
      list vsiMacLimit {
        key "vsiName";
        description
          "VSI MAC address limit.";
        leaf vsiName {
          type string {
            length "1..31";

          }
          description
            "VSI name.";
        }
        leaf maximum {
          type uint32 {
            range "0..524288";
          }
          must "not(../rate=0) or (../rate=0 and ../maximum>0)";
          mandatory true;
          description
            "Maximum number of MAC addresses that can be learned in a 
             VSI.";
        }
        leaf rate {
          type uint16 {
            range "0..1000";
          }
          must "not(../maximum=0) or (../maximum=0 and ../rate>0)";
          default "0";
          description
            "Interval at which MAC addresses are learned in a VSI.";
        }
        leaf action {
          type macLimitForward;
          default "discard";
          description
            "Discard or forward after the number of learned MAC 
             addresses reaches the maximum number in a VSI.";
        }
        leaf alarm {
          type macEnableStatus;
          default "disable";
          description
            "Whether an alarm is generated after the number of learned 
             MAC addresses reaches the maximum number in a VSI.";
        }
        leaf upThreshold {
          type uint8 {
            range "80..100";
          }
          must "(../upThreshold>=../downThreshold)";
          mandatory true;
          description
            "Upper limit for the number of MAC addresses.";
        }
        leaf downThreshold {
          type uint8 {
            range "60..100";
          }
          mandatory true;

          description
            "Upper limit for the number of MAC addresses.";
        }
      }
    }

           container bdMacLimits {
      description
        "BD MAC address limit list.";
      list bdMacLimit {
        key "bdId";
        description
          "BD MAC address limit.";
        leaf bdId {
          type uint32 {
            range "1..16777215";
          }
          description
            "Specifies the ID of a bridge domain.";
        }
        leaf maximum {
          type uint32 {
            range "0..130048";
          }
          must "not(../rate=0) or (../rate=0 and ../maximum>0)";
          mandatory true;
          description
            "Maximum number of MAC addresses that can be learned in a 
             BD.";
        }
        leaf rate {
          type uint16 {
            range "0..1000";
          }
          default "0";
          description
            "Interval at which MAC addresses are learned in a BD.";
        }
        leaf action {
          type macLimitForward;
          default "discard";
          description
            "Forward or discard the packet.";
        }
        leaf alarm {
          type macEnableStatus;
          default "enable";
          description
            "Whether an alarm is generated after the number of learned 
             MAC addresses reaches the maximum number.";
        }
      }
    }

    container ifMacLimits {
      description
        "Interface MAC address limit list.";
      list ifMacLimit {
        key "ifName limitType";
        description
          "Interface MAC address limit.";
        leaf ifName {
          type string;
          description
            "Interface name.";
        }
        leaf limitType {
          type limitType;
          description
            "Interface MAC limit type.";
        }
        leaf ruleName {
          type leafref {
            path "/mac/macLimitRules/macLimitRule/ruleName";
          }
          description
            "Rule name.";
        }
        leaf maximum {
          when "not(../limitType='macApply') 
                or ../limitType='macLimit'";
          type uint32 {
            range "0..131072";
          }
          must "not(../rate=0) or (../rate=0 and ../maximum>0)";
          mandatory true;
          description
            "Maximum number of MAC addresses that can be learned 
             on an interface.";
        }
        leaf rate {
          when "not(../limitType='macApply') 
                or ../limitType='macLimit'";
          type uint16 {
            range "0..1000";
          }
          must "not(../maximum=0) or (../maximum=0 and ../rate>0)";
          default "0";
          description
            "Interval (ms) at which MAC addresses are learned on 
             an interface.";
        }

        leaf action {
          when "not(../limitType='macApply') 
                or ../limitType='macLimit'";
          type macLimitForward;
          default "discard";
          description
            "Discard or forward after the number of learned MAC 
             addresses reaches the maximum number on an interface";
        }
        leaf alarm {
          when "not(../limitType='macApply') 
                or ../limitType='macLimit'";
          type macEnableStatus;
          default "enable";
          description
            "Whether an alarm is generated after the number of learned 
             MAC addresses reaches the maximum number on an interface.";
        }
      }
    }
    container ifVlanMacLimits {
      description
        "Interface + VLAN MAC address limit list.";
      list ifVlanMacLimit {
        key "ifName vlanBegin limitType";
        config false;
        description
          "Interface + VLAN MAC address limit.";
        leaf ifName {
          type string;
          description
            "Name of an interface. ";
        }
        leaf vlanBegin {
          type macVlanId;
          description
            "Start VLAN ID.";
        }
        leaf vlanEnd {
          type macVlanId;
          must "(../vlanEnd>=../vlanBegin) 
                or not(../limitType='macApply')";
          description
            "End VLAN ID.";
        }
        leaf limitType {
          type limitType;
          description
            "Interface MAC limit type.";
        }
        leaf ruleName {
          type leafref {
            path "/mac/macLimitRules/macLimitRule/ruleName";

          }
          description
            "Rule name.";
        }
        leaf maximum {
          when "not(../limitType='macApply') 
                or ../limitType='macLimit'";
          type uint32 {
            range "0..131072";
          }
          mandatory true;
          description
            "Maximum number of MAC addresses that can be learned on
             an interface.";
        }
        leaf rate {
          when "not(../limitType='macApply') 
                or ../limitType='macLimit'";
          type uint16 {
            range "0..1000";
          }
          mandatory true;
          description
            "Interval (ms) at which MAC addresses are learned on 
             an interface.";
        }
        leaf action {
          when "not(../limitType='macApply') 
                or ../limitType='macLimit'";
          type macLimitForward;
          default "discard";
          description
            "Discard or forward the packet.";
        }
        leaf alarm {
          when "not(../limitType='macApply') 
                or ../limitType='macLimit'";
          type macEnableStatus;
          default "enable";
          description
            "Whether an alarm is generated after the number of learned 
             MAC addresses reaches the maximum number.";
        }
      }
    }
  }
}
