module ietf-microwave-radio-link { 
  yang-version 1.1; 
  namespace "urn:ietf:params:xml:ns:yang:ietf-microwave-radio-link"; 
  prefix mrl; 

  import ietf-yang-types { 
    prefix yang; 
  } 

  import ietf-interfaces { 
    prefix if; 
  } 

  import iana-if-type { 
    prefix ianaift; 
  }

  organization 
    "IETF CCAMP Working Group"; 
  contact 
    "jonas.ahlberg@ericsson.com 
     amy.yemin@huawei.com 
     Xi.Li@neclab.eu 
     cjbc@it.uc3m.es 
     k-kawada@ah.jp.nec.com"; 

  description 
    "This is a module for the entities in a generic 
     microwave system.";  

  revision 2016-12-22 { 
    description 
      "Draft revision covering a complete scope for  
      configuration and state data for radio link  
      interfaces."; 

      reference ""; 
  } 
  revision 2016-10-29 { 
    description 
      "Draft revision."; 
    reference ""; 
  }

  /* 
  * Features 
  */ 

  feature xpic { 
    description 
      "Indicates that the device supports XPIC."; 
  } 

  feature mimo { 
    description 
      "Indicates that the device supports MIMO."; 
  } 

  feature tdm {
    description
      "Indicates that the device supports TDM.";
  }

  /* 
  * Interface identities 
  */ 

  identity radio-link-terminal { 
    base ianaift:iana-interface-type; 
    description 
      "Interface identity for a radio link terminal."; 
  } 

  identity carrier-termination { 
    base ianaift:iana-interface-type; 
    description 
      "Interface identity for a carrier termination."; 
  }

 /* 
  * Radio-link-terminal mode identities 
  */ 
  identity rlt-mode { 
    description 
      "A description of the mode in which the radio  
      link terminal is configured. The format is X  
      plus Y. X represent the number of bonded  
      carrier terminations. Y represent the number  
      of protecting carrier terminations.";   
  }        

  identity one-plus-zero { 
    base rlt-mode; 
    description 
      "1 carrier termination only."; 
  } 

  identity one-plus-one { 
    base rlt-mode; 
    description 
      "1 carrier termination 
       and 1 protecting carrier termination."; 
  }  

  identity two-plus-zero { 
    base rlt-mode; 
    description 
      "2 bonded carrier terminations."; 
  }

  /* 
  * Coding and modulation identities 
  */ 

  identity coding-modulation { 
    description 
      "The coding and modulation schemes."; 
  }

  identity half-bpsk-strong { 
    base coding-modulation; 
    description 
    "Half BPSK strong coding and modulation scheme."; 
  }
  identity half-bpsk { 
    base coding-modulation; 
    description 
      "Half BPSK coding and modulation scheme."; 
  }

  identity half-bpsk-light { 
    base coding-modulation; 
    description 
      "Half BPSK light coding and modulation scheme."; 
  } 

  identity bpsk-strong { 
    base coding-modulation; 
    description 
      "BPSK strong coding and modulation scheme."; 
  }        

  identity bpsk {
    base coding-modulation;
    description
      "BPSK coding and modulation scheme.";
  }

    identity bpsk-light {
    base coding-modulation;
    description
      "BPSK light coding and modulation scheme.";
  }      

  identity qpsk {
    base coding-modulation;
    description
      "QPSK coding and modulation scheme.";
  }    

  identity qam-4-strong {
    base coding-modulation;
    description
      "4 QAM strong coding and modulation scheme.";
  }

  identity qam-4 {
    base coding-modulation;
    description
      "4 QAM coding and modulation scheme.";
  }  
  identity qam-4-light {
    base coding-modulation;
    description
      "4 QAM light coding and modulation scheme.";
  }

  identity qam-16-strong {
    base coding-modulation;
    description
      "16 QAM strong coding and modulation scheme.";
  }

  identity qam-16 {
    base coding-modulation;
    description
      "16 QAM coding and modulation scheme.";
  }

  identity qam-16-light {
    base coding-modulation;
    description
      "16 QAM light coding and modulation scheme.";
  }

  identity qam-32-strong {
    base coding-modulation;
    description
      "32 QAM strong coding and modulation scheme.";
  }

  identity qam-32 {
    base coding-modulation;
    description
      "32 QAM coding and modulation scheme.";
  }

  identity qam-32-light {
    base coding-modulation;
    description
      "32 QAM light coding and modulation scheme.";
  }

  identity qam-64-strong {
    base coding-modulation;
    description
      "64 QAM strong coding and modulation scheme.";
  }       
  identity qam-64 {
    base coding-modulation;
    description
      "64 QAM coding and modulation scheme.";
  }

  identity qam-64-light {
    base coding-modulation;
    description
      "64 QAM light coding and modulation scheme.";
  }

  identity qam-128-strong {
    base coding-modulation;
    description
      "128 QAM strong coding and modulation scheme.";
  }

  identity qam-128 {
    base coding-modulation;
    description
      "128 QAM coding and modulation scheme.";
  }

  identity qam-128-light {
    base coding-modulation;
    description
      "128 QAM light coding and modulation scheme.";
  }

  identity qam-256-strong {
    base coding-modulation;
    description
      "256 QAM strong coding and modulation scheme.";
  }

  identity qam-256 {
    base coding-modulation;
    description
      "256 QAM coding and modulation scheme.";
  }

  identity qam-256-light {
    base coding-modulation;
    description
      "256 QAM light coding and modulation scheme.";
  }        
  identity qam-512-strong {
    base coding-modulation;
    description
      "512 QAM strong coding and modulation scheme.";
  }

  identity qam-512 {
    base coding-modulation;
    description
      "512 QAM coding and modulation scheme.";
  }

  identity qam-512-light {
    base coding-modulation;
    description
      "512 QAM light coding and modulation scheme.";
  }

  identity qam-1024-strong {
    base coding-modulation;
    description
      "1024 QAM strong coding and modulation scheme.";
  }

  identity qam-1024 {
    base coding-modulation;
    description
      "1024 QAM coding and modulation scheme.";
  }

  identity qam-1024-light {
    base coding-modulation;
    description
      "1024 QAM light coding and modulation scheme.";
  }

  identity qam-2048-strong {
    base coding-modulation;
    description
      "2048 QAM strong coding and modulation scheme.";
  }

  identity qam-2048 {
    base coding-modulation;
    description
      "2048 QAM coding and modulation scheme.";
  }
  identity qam-2048-light {
    base coding-modulation;
    description
      "2048 QAM light coding and modulation scheme.";
  }

  identity qam-4096-strong {
    base coding-modulation;
    description
      "4096 QAM strong coding and modulation scheme.";
  }

  identity qam-4096 {
    base coding-modulation;
    description
      "4096 QAM coding and modulation scheme.";
  }

  identity qam-4096-light {
    base coding-modulation;
    description
      "4096 QAM light coding and modulation scheme.";
  }

  /*
   * Protection architecture type identities
  */
  identity protection-architecture-type {
    description
      "protection architecture type";
  }

  identity one-plus-one-type {
    base protection-architecture-type;
    description
      "One carrier termination and
      one protecting carrier termination.";
  }

  identity one-to-n-type { 
    base protection-architecture-type; 
    description 
      "One carrier termination protecting 
       n other carrier terminations."; 
  } 
  /*
   * Protection states identities
   */

  identity protection-states {
    description
     "Identities describing the status of the protection,
     in a group of carrier terminations configured in 
     a radio link protection mode.";
  }

  identity unprotected {
    base protection-states;
    description "Not protected";
  }  

  identity protected {
    base protection-states;
    description "Protected";
  }

  identity unable-to-protect {
    base protection-states;
    description "Unable to protect";
  }  

  /*
   * protection-external-commands identities
   */          

  identity protection-external-commands{
    description
      "Protection external commands for trouble shooting 
      purpose.";
  }

  identity manual-switch{
    base protection-external-commands;
    description
      "A switch action initiated by an operator command. 
      It switches normal traffic signal to the protection 
      transport entity.";
  }
  /* 
  * TDM-type identities 
  */    
  identity tdm-type {
    description
      "A description of the type of TDM connection,
      also indicating the supported capacity of the
      connection.";  
  }

  identity E1 {
    base tdm-type;
    description
      "E1 connection, 2,048 Mbit/s.";
  }

  identity STM-1 {
    base tdm-type;
    description
      "STM-1 connection, 155,52 Mbit/s.";
  }

  /*
   * Typedefs
   */
  typedef power {
    type decimal64 {
      fraction-digits 1;
    }
    description 
      "Type used for power values, selected and measured.";
  }

  /* 
  * Radio Link Terminal (RLT) - Configuration data nodes 
  */        
  augment "/if:interfaces/if:interface" {
    when "if:type = 'mrl:radio-link-terminal'";
    description
      "Addition of data nodes for radio link terminal to 
       the standard Interface data model, for interfaces of
       the type 'radio-link-terminal'.";
    leaf id {
      type string;
      default ""; 
      description
        "ID of the radio link terminal. Used by far-end when
         checking that it's connected to the correct RLT.";
    } 
	
    leaf mode {
      type identityref {
        base rlt-mode;
      }
      mandatory true;
      description
        "A description of the mode in which the radio link 
         terminal is configured. The format is X plus Y.
         X represent the number of bonded carrier terminations.
         Y represent the number of protecting carrier 
         terminations.";
    }

    leaf-list carrier-terminations {
      type if:interface-ref;
      must "/if:interfaces/if:interface[if:name = current()]"
         + "/if:type = 'mrl:carrier-termination'" {
        description        
          "The type of interface must be 
           'carrier-termination'.";
      }
      min-elements 1;
      description
        "A list of references to carrier terminations
         included in the radio link terminal.";
    }

    leaf-list rlp-groups {
      type leafref {
        path "/mrl:radio-link-protection-groups/"
           + "mrl:radio-link-protection-group/mrl:name";
      }
      description
        "A list of references to the carrier termination
         groups configured for radio link protection in this 
         radio link terminal.";
    }
    leaf-list xpic-pairs {
      if-feature xpic;
      type leafref {
        path "/mrl:xpic-pairs/mrl:xpic-pair/mrl:name";
      }
      description
        "A list of references to the XPIC pairs used in this 
         radio link terminal. One pair can be used by two 
         terminals.";
    }

    leaf mimo-group {
      if-feature mimo;
      type leafref {
        path "/mrl:mimo-groups/mrl:mimo-group/mrl:name";
      }
      description
        "A reference to the MIMO group used in this 
         radio link terminal. One group can be used by more
         than one terminal.";
    }

    list tdm-connections {
      if-feature tdm;
      key "tdm-type";
      description 
       "A list stating the number of TDM connections of a 
       specified tdm-type that is supported by the RLT.";  
      leaf tdm-type {
        type identityref {
          base tdm-type;
        }
        description 
          "The type of TDM connection, which also indicates
          the supported capacity.";
      }

      leaf tdm-connections {
        type uint16;
        mandatory true;
        description "Number of connections of the specified type.";
      }
    }
  }
  /*
   * Carrier Termination - Configuration data nodes
   */

  augment "/if:interfaces/if:interface" {
    when "if:type = 'mrl:carrier-termination'";
    description 
      "Addition of data nodes for carrier termination to  
      the standard Interface data model, for interfaces  
      of the type 'carrier-termination'."; 
    leaf carrier-id {
      type string;
      default "A";
      description
        "ID of the carrier. (e.g. A, B, C or D)
         Used in XPIC & MIMO configurations to check that 
         the carrier termination is connected to the correct 
         far-end carrier termination. Should be the same 
         carrier ID on both sides of the hop.
         Defaulted when not MIMO or XPIC.";
    }

    leaf tx-enabled {
      type boolean;
      default "false";
      description
        " Disables (false) or enables (true) the  
        transmitter.Only applicable when the interface  
        is enabled (interface:enabled = true) otherwise  
        it's always disabled."; 
    } 

    leaf tx-frequency {
      type uint32;
      units "kHz";
      mandatory true;
      description
        "Selected transmitter frequency.";
    }
    leaf rx-frequency {
      type uint32;
      units "kHz";
      description
        "Selected receiver frequency.
         Mandatory and writeable when rx-frequency-config=true.
         Otherwise read-only and calculated from tx-frequency 
         and duplex-distance.";
    }

    leaf rx-frequency-config {
      type boolean;
      default "true";
      description 
        "Enable (true) or disable (false) direct  
         configuration of rx-frequency and instead  
         using a defined duplex distance."; 
    }  

    leaf duplex-distance {
      when "../rx-frequency-config = 'false'";
      type uint32;
      units "kHz";
      mandatory true;
      description
        "Distance between Tx & Rx frequencies.
         Used to calaculate rx-frequency when 
         rx-frequency-config=false.";
    }

    leaf channel-separation {
      type decimal64 {
        fraction-digits 1;
      }
      units "MHz";
      mandatory true;
      description
        "The amount of bandwidth allocated to a carrier.";
    } 	
	
    leaf polarization {
      type enumeration {
        enum "horizontal" {
          description "Horizontal polarization.";
        }
        enum "vertical" {
          description "Vertical polarization.";
        }
        enum "not-specified" {
          description "Polarization not specified.";
        }
      }
      default "not-specified";
      description
        "Polarization - A textual description for info only.";
    }

    leaf power-mode {
      type enumeration {    
        enum rtpc {
          description "Remote Transmit Power Control (RTPC).";
        }
        enum atpc {
          description "Automatic Transmit Power Contro 
                       (ATPC).";
        }
      }
      mandatory true;
      description
        "A choice of Remote Transmit Power Control (RTPC)
         or Automatic Transmit Power Control (ATPC).";
    }

    leaf selected-output-power {
      type power {
        range "-99..40";
      }
      units "dBm";
      mandatory true;
      description
        "Selected output power in RTPC mode and selected 
        maximum selected maximum output power in ATPC mode. 
        Minimum ouput power in ATPC mode is the same as the
        system capability, available-min-output-power."; 
    } 

    leaf atpc-lower-threshold {
      when "../power-mode = 'atpc'";
      type power {
        range "-99..-30";
      }
      units "dBm";
      mandatory true;
      description
        "The lower threshold for the input power at far-end used in
        the ATPC mode.";
    }

    leaf atpc-upper-threshold {
      when "../power-mode = 'atpc'";
      type power {
        range "-99..-30";
      }
      units "dBm";
      mandatory true;
      description
        "The upper threshold for the input power  
         at far-end used in the ATPC mode."; 
    }      

    leaf coding-modulation-mode {
      type enumeration {
        enum fixed {
          description "Fixed coding/modulation."; 
        }
        enum adaptive {
          description "Adaptive coding/modulation.";
        }
      }
      mandatory true;
      description
        "A selection of fixed or 
         adaptive coding/modulation mode.";
    }

    leaf selected-cm {
      when "../coding-modulation-mode = 'fixed'";
      type identityref {
        base coding-modulation;        
      }
      mandatory true;
      description
        "Selected fixed coding/modulation.";
    }
    leaf selected-min-acm {
      when "../coding-modulation-mode = 'adaptive'";
      type identityref {
        base coding-modulation;
      }
      mandatory true;
      description
        "Selected minimum coding/modulation.
         Adaptive coding/modulation shall not go
         below this value.";
    }

    leaf selected-max-acm {
      when "../coding-modulation-mode = 'adaptive'";
      type identityref {
        base coding-modulation;
      }    
      mandatory true;
      description
        "Selected maximum coding/modulation.
         Adaptive coding/modulation shall not go
         above this value.";
    }

    leaf if-loop {
      type enumeration {
        enum disabled {
          description "Disables the IF Loop.";
        }
        enum client {
          description "Loops the signal back to the client side.";
        }
        enum radio {
          description "Loops the signal back to the radio side.";
        }
      }
      default "disabled";
      description
        "Enable (client/radio) or disable (disabled) the IF loop,
        which loops the signal back to the client side or the  
        radio side."; 
    } 
    leaf rf-loop {
      type enumeration {
        enum disabled {
          description "Disables the RF Loop.";
        }
        enum client {
          description "Loops the signal back to the client side.";
        }
        enum radio {
          description "Loops the signal back to the radio side.";
        } 
      }
      default "disabled";
      description
        "Enable (client/radio) or disable (disabled) the RF loop,
        which loops the signal back to the client side or
        the radio side.";
    }    

    container ct-performance-thresholds {
      description
        "Specification of thresholds for when alarms should
         be sent and cleared for various performance counters.";

      leaf received-level-alarm-threshold {
        type power {
          range "-99..-30";
        }
        units "dBm";
        default "-99";
        description
          "Specification of at which received power level an alarm
          should be raised.";
      }

      leaf transmitted-level-alarm-threshold {
        type power {
          range "-99..40";
        }
        units "dBm";
        default "-99";
        description 
          "An alarm is sent when the transmitted power level 
           is below the specified threshold."; 
      } 
      leaf ber-alarm-threshold {
        type enumeration {
          enum "10e-9" {
            description "Threshold at 10e-9.";
          }
          enum "10e-8" {
            description "Threshold at 10e-8.";
          }
          enum "10e-7" {
            description "Threshold at 10e-7.";
          }
          enum "10e-6" {
            description "Threshold at 10e-6.";
          }
          enum "10e-5" {
            description "Threshold at 10e-5.";
          }
          enum "10e-4" {
            description "Threshold at 10e-4.";
          }     
          enum "10e-3" {
            description "Threshold at 10e-3.";
          }
          enum "10e-2" {
            description "Threshold at 10e-2.";
          }
          enum "10e-1" {
            description "Threshold at 10e-1.";
          }
        }
        default "10e-6";
        description
          "Specification of at which BER an alarm should 
           be raised.";
      }
    }
  }

  /*
   * Radio Link Terminal - Operational state data nodes
   * Currently nothing in addition to the general
   * interface-state model.
   */

  /*
   * Carrier Termination - Operational state data nodes
   */
  augment "/if:interfaces-state/if:interface" {
    when "if:type = 'mrl:carrier-termination'";
    description
      "Addition of state data nodes for carrier termination to 
       the standard Interface state data model, for interfaces 
       of the type 'carrier-termination'.";

    leaf tx-oper-status {
      type enumeration {
        enum "off" {
          description "Transmitter is off.";
        }
        enum "on" {
          description "Transmitter is on.";
        }
        enum "standby" {
          description "Transmitter is in standby.";
        }
      }
      description
        "Shows the operative status of the transmitter.";
    }    

    leaf actual-transmitted-level { 
        type power { 
          range "-99..40"; 
        } 
      units "dBm";
      description
        "Actual transmitted power level (0.1 dBm resolution).";
    }

    leaf actual-received-level {
      type power {
        range "-99..-20";
      }
      units "dBm";
      description
        "Actual received power level (0.1 dBm resolution).";
    } 
	
    leaf actual-tx-cm {
      type identityref {
         base coding-modulation;
      }
      description
        "Actual coding/modulation in transmitting direction.";
    }
    leaf actual-snir {
      type decimal64 {
        fraction-digits 1;
        range "0..99";
      }
      units "dB";
      description
        "Actual signal to noise plus interference ratio.
         (0.1 dB resolution).";
    }

    leaf actual-xpi {
      if-feature xpic;
      type decimal64 {
        fraction-digits 1; 
        range "0..99";
      }
      units "dB";
      description
        "The actual carrier to cross-polar interference.
         Only valid if XPIC is enabled. (0.1 dB resolution).";
    }

    container capabilities {
      description
        "Capabilities of the the installed equipment and 
         some selected configurations.";        

      leaf min-tx-frequency {
        type uint32;
        units "kHz";
        description
          "Minimum Tx frequency possible to use.";
      }

      leaf max-tx-frequency {
        type uint32;
        units "kHz";
        description 
          "Maximum Tx frequency possible to use."; 
      }
      leaf min-rx-frequency {
        type uint32;
        units "kHz";
        description
          "Minimum Rx frequency possible to use.";
      }

      leaf max-rx-frequency {
        type uint32;
        units "kHz";
        description
          "Maximum Tx frequency possible to use.";
      }

      leaf available-min-output-power {
        type power; 
        units "dBm";
        description
          "The minimum output power supported.";
      }    

      leaf available-max-output-power {
        type power;
        units "dBm";
        description
          "The maximum output power supported.";
      }

      leaf available-min-acm {
        type identityref {
          base coding-modulation;
        }
        description
          "Minimum coding-modulation possible to use.";
      }

      leaf available-max-acm {
        type identityref {
          base coding-modulation;
        }
        description
          "Maximum coding-modulation possible to use.";
      }
    }
  } 
  augment "/if:interfaces-state/if:interface/if:statistics" {
    when "../if:type = 'mrl:carrier-termination'";
    description
      "Addition of state data nodes in the container statistics
       for carrier terminations to the standard Interface data 
       model, for interfaces of the type 'carrier-termination'.";

    leaf bbe {
      type yang:counter32;
      units "number of block errors";
      description
        "Number of Background Block Errors (BBE) during the
        interval. A BBE is an errored block not occurring as
        part of an SES.";
    }

    leaf es {
      type yang:counter32;
      units "seconds";
      description    
      "Number of Errored Seconds (ES) since last  
       reset. An ES is a one-second period with  
       one or more errored blocks or at least one  
       defect."; 
      } 

    leaf ses {
      type yang:counter32;
      units "seconds";
      description
        "Number of Severely Errored Seconds (SES) during the
         interval. SES is a one-second period which contains
         equal or more than 30% errored blocks or at least
         one defect. SES is a subset of ES.";
    }

    leaf uas {
      type yang:counter32;
      units "seconds";
      description
        "Number of Unavailable Seconds (UAS), that is, the
         total time that the node has been unavailable during
         a fixed measurement interval.";
    }
    leaf min-rltm {
      type power {
        range "-99..-20";
      }
      units "dBm";
      description
        "Minimum received power level since last reset.";
    }

    leaf max-rltm {
      type power {
        range "-99..-20";
      }
      units "dBm";
      description
        "Maximum received power level since last reset.";
    }

    leaf min-tltm {
      type power {
        range "-99..40";    
      }
      units "dBm";
      description
        "Minimum transmitted power level since last reset.";
    }

    leaf max-tltm {
      type power {
        range "-99..40";
      }
      units "dBm";
      description
        "Maximum transmitted power level since last reset.";
    }
  }

  /*
   * Radio Link Protection Groups - Configuration data nodes
   */

  container radio-link-protection-groups {
    description
      "Configuration of radio link protected groups  
      (1+1) of carrier terminations in a radio link.  
      More than one protected group per radio-link-terminal
      is allowed."; 
    list radio-link-protection-group {
      key "name";
      description
      "List of protected groups of carrier terminations
      in a radio link.";

      leaf name {
        type string;
        description
          "Name used for identification of the radio
           link protection group";
      }

      leaf protection-architecture-type { 
        type identityref{ 
          base protection-architecture-type; 
        } 
        default "one-plus-one-type"; 
        description 
          "The type of protection architecture  
          used, e.g. one carrier termination  
          protecting one carrier termination."; 
      }   
	  
      leaf protection-operation-type { 
        type enumeration { 
          enum "non-revertive" { 
            description 
              "In non revertive operation, the  
              traffic does not return to the  
              working carrier termination if the  
              switch requests are terminated. "; 
              } 
          enum "revertive" { 
            description 
              "In revertive operation, the  
              traffic always returns to (or  
              remains on) the working carrier  
              termination if the switch requests  
              are terminated. "; 
            } 
          } 
          default "non-revertive"; 
          description  
            "The type of protection operation, i.e.  
            revertive or non-revertive operation."; 
          } 
      leaf-list working-entity  { 
        when "../protection-operation-type =  'revertive'"; 
        type if:interface-ref; 
        must "/if:interfaces/if:interface[if:name = current()]" 
           + "/if:type = 'mrl:carrier-termination'" { 
           description 
             "The type of a working-entity must be  
             'carrier-termination'."; 
           } 
           min-elements 1; 
           description 
           "The carrier terminations over which the  
           traffic normally should be transported  
           over when there is no need to use the  
           protecting carrier termination."; 
        } 

      leaf revertive-wait-to-restore { 
        when "../protection-operation-type = 'revertive'"; 
        type uint16; 
        units "seconds"; 
        default "0"; 
        description 
          "The time to wait before switching back  
          to the working carrier termination if  
          protection-operation-type is revertive."; 
        } 

      leaf-list radio-link-protection-members { 
        type if:interface-ref; 
        must "/if:interfaces/if:interface[if:name = current()]" 
          + "/if:type = 'mrl:carrier-termination'" { 
          description 
            "The type of a protection member must  
            be 'carrier-termination'."; 
          } 
          min-elements 2; 
          description 
            "Association to a group of carrier  
            terminations configured for radio link  
            protection and used in the radio link terminal."; 
        } 
      action protection-external-commands { 
        input { 
          leaf protection-external-command { 
            type identityref { 
              base protection-external-commands; 
            }
            description 
              "Execution of protection external
               commands for trouble shooting purpose.";    
          } 
        } 
      } 
    } 
} 

  /* 
  * Radio Link Protection - Operational state data nodes 
  */         
  container radio-link-protection-groups-state {     
    config false; 
    description 
      "State data for radio link protected groups  
      of carrier terminations in a radio link.";    
      list radio-link-protection-group { 
        key "name"; 
        description 
          "List of protected groups of carrier  
          terminations in a radio link."; 

      leaf name { 
        type string; 
        description 
          "Name used for identification of the  
           radio link protection group."; 
      } 

      leaf protection-status { 
        type identityref { 
          base protection-states; 
        } 
        description 
          "Status of the protection, in a group of  
          carrier terminations configured in a  
          radio link protection mode."; 
        } 
    } 
  }  
  /* 
  * XPIC & MIMO - Configuration data nodes 
  */ 

  container xpic-pairs { 
    if-feature xpic; 
      description 
        "Configuration of carrier termination pairs 
        for operation in XPIC mode."; 

    list xpic-pair { 
      key "name"; 
      description 
        "List of carrier termination pairs in XPIC mode."; 

    leaf name { 
      type string; 
      description 
        "Name used for identification of the XPIC pair."; 
    }      
    leaf enabled { 
        type boolean; 
        default "false"; 
        description 
          "Enable(true)/disable(false) XPIC"; 
      } 

      leaf-list xpic-members { 
        type if:interface-ref; 
        must "/if:interfaces/if:interface[if:name = current()]" 
          + "/if:type = 'mrl:carrier-termination'" { 
          description 
            "The type of a xpic-member must be  
            'carrier-termination'."; 
          } 
          min-elements 2; 
          max-elements 2; 
          description 
            "Association to XPIC pairs used in the  
            radio link terminal."; 
           } 
         } 
  }
  container mimo-groups { 
    if-feature mimo; 
    description 
      "Configuration of carrier terminations 
      for operation in MIMO mode."; 

      list mimo-group { 
        key "name"; 
        description 
          "List of carrier terminations in MIMO mode."; 

      leaf name { 
        type string; 
        description 
        "Name used for identification of the MIMO group."; 
      } 

      leaf enabled { 
        type boolean;     
        default "false"; 
        description 
          "Enable(true)/disable(false) MIMO"; 
    } 

      leaf-list mimo-members { 
        type if:interface-ref; 
        must "/if:interfaces/if:interface[if:name = current()]" 
           + "/if:type = 'mrl:carrier-termination'" { 
           description 
             "The type of a mimo-member must be  
             'carrier-termination'."; 
           } 
           min-elements 2; 
           description 
             "Association to a MIMO group if used in  
             the radio link terminal."; 

        } 
      } 
    }         
}
