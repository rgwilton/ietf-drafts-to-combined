module ietf-nvo-tp-types {
    namespace "urn:ietf:params:xml:ns:yang:ietf-nvo-tp-types";
    prefix TPTypes;

    import ietf-nvo-common-types {prefix  CommonTypes;}
    import ietf-yang-types { prefix yang;     }
      import ietf-nvo-qos-types { prefix QosTypes;}

    organization "";
    contact "";
    description "ietf-nvo-tp-types";
    revision 2016-10-24 {
        reference "draft-chen-opsawg-composite-vpn-dm-00";
    }

    //LayerRate parameters.
    grouping PwSpec {
        description "PwSpec Grouping.";

        leaf controlWord {
            type boolean;
            default false;
            description "controlWord";
        }
        leaf pwVlanAction {
            type TPTypes:PWTagMode;
            description "pwVlanAction";
        }
    }

    grouping IpSpec {
        description "IpSpec Grouping.";

        leaf masterIp {
            type string;
            description "master IP address";
        }
        leaf mtu {
            type uint64;
            description "mtu for ip layer,scope:46~9600";
        }
    }

    grouping EthernetSpec {
        description "EthernetSpec Grouping.";

        leaf accessType {
            type CommonTypes:EthernetEncapType;
            description "access frame type";
        }

        choice accessVlanValue {
            description "accessVlanValue";
            case QinQVlan {
                container qinqVlan {
                    description "qinqVlan";
                    uses TPTypes:QinQVlan;
                }
            }

            case DOT1Q {
                container dot1q {
                    description "dot1q";
                    uses TPTypes:Dot1QVlan;
                }
            }
        }

        leaf vlanAction {
            type CommonTypes:EthernetAction;
            description "Frame type that can be accepted. not needed
            now";
        }

        leaf actionValue{
            type string{length "0..100";}
            description "action value";
        }
    }

    grouping QinQVlan {
        description "QinQVlan Grouping.";

        leaf-list cvlanList {
            type uint64;
            description "cvlanList";
        }
        leaf svlanList {
            type uint64;
            description "svlanList";
        }
    }

    grouping Dot1QVlan {
        description "Dot1QVlan Grouping.";

        leaf-list dot1qVlanList {
            type uint64;
            description "dot1qVlanList";
        }
    }

    grouping VxlanSpec {
        description "VxlanSpec Grouping.";

        leaf vni {
            type uint32;
            description "vni";
        }

        leaf vtepIP {
            type string;
            description "vtep ip";
        }
    }

    //CE spec
    grouping CeTp {
        description "CeTp Grouping.";

        leaf ceID {
            type yang:uuid;
            description "Site router ID";
        }

        leaf ceDirectNeID {
            type yang:uuid;
            description "direction connected NE ID, only valid in
            asbr ";
        }

        leaf ceDirectTPID {
            type yang:uuid;
            description "ce Direct TP id, only valid in asbr";
        }

        leaf ceIfmasterIp {
            type string;
            description "ceIfmasterIp";
        }

        leaf location {
            type string {length "0..400";}
            description "CE device location ";
        }
    }

    //TPBasicInfo
    grouping TPBasicInfo {
        description "TPBasicInfo Grouping.";

        leaf edgePointRole {
            type CommonTypes:EdgePointRole;
            description "edge role for TP, for example:UNI/NNI ";
        }
        leaf topologyRole {
            type CommonTypes:TopoNodeRole;
            description "hub/spoke role, etc";
        }

        leaf Type
        {
            type CommonTypes:TpType;
            description "Type";
        }

        leaf workingLayer {
            type CommonTypes:LayerRate;
            description "working layer";
        }

        list typeSpecList {
            key "layerRate";
            uses TPTypes:TpTypeSpec;
            description "typeSpecList";
        }

        leaf adminStatus {
            type CommonTypes:AdminStatus;
            description "administrative status.";
        }

        container tpQosNode {
            description "tpQosNode";
            uses QosTypes:TPQosNode;
        }

        container flowServices{
            description "flow services in one TP";
            uses QosTypes:FlowServices;
        }

        list addtionalInfo {
            key "name";
            uses CommonTypes:nvstring;
            description "addtionalInfo";
        }
    }

    //TpTypeSpec
    grouping TpTypeSpec{
        description "TpTypeSpec Grouping.";

        leaf layerRate {
            type CommonTypes:LayerRate;
            description "layerRate";
        }

        choice specValue {
            description "specValue";
            case LR_Ethernet {
                container ethernetSpec {
                    description "ethernetSpec";
                    uses TPTypes:EthernetSpec;
                }
            }
            case LR_IP {
                container ipSpec {
                    description "ipSpec";
                    uses TPTypes:IpSpec;
                }
            }
            case LR_Vxlan {
                container vxlanSpec {
                    description "vxlanSpec";
                    uses TPTypes:VxlanSpec;
                }
            }
        }
    }

    //----------------------------------------------//
    //typedef
    //----------------------------------------------//
    typedef PWTagMode {
        type enumeration {
            enum RAW{
                description "RAW";
            }
            enum TAGGED{
                description "TAGGED";
            }
        }
        description "PWTagMode";
    }
}
