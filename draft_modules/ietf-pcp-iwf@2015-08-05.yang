module ietf-pcp-iwf {
  namespace "urn:ietf:params:xml:ns:yang:ietf-pcp-iwf";
  prefix pcp-iwf;

  import ietf-inet-types { prefix inet; }
  import ietf-pcp { prefix pcp; }

  organization "xxxx Working Group";
  contact
     "Mohamed Boucadair <mohamed.boucadair@orange.com>
      Christian Jacquenet <christian.jacquenet@orange.com>";

  description
       "This module contains a collection of YANG definitions for
        UPnP IGD/PCP Interworking implementations.

        Copyright (c) 2016 IETF Trust and the persons identified as
        authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).

        This version of this YANG module is part of RFC XXXX; see
        the RFC itself for full legal notices.";

  revision 2015-08-05 {
      description "Changes xxxx.";
       reference "xxxx";
   }

// IGD versions

grouping igd-version {
    description
      "UPnp IGD Version";

   leaf igd-version {
      type enumeration {

         enum "igd:1" {
             description
               "UPnP IGD:1";
         }

         enum "igd:2" {
             description
              "UPnP IGD:2";
         }

         enum "both" {
             description
              "UPnP IGD:1 and UPnP IGD:2";
         }
      }
   description
    "UPnP IGD Version";
 }
}

/*
  *PCP Configuration
  */

    container pcp-iwf-config {
       description
         "UPnP IGD/PCP Interworking Function";

       leaf enable {
            type boolean;
            description
              "Enable/Disable the UPnP IGD-PCP IWF";
       }

      container pcp-igd-iwf-instances {
           description
             "UPnP IGD/PCP Interworking Function instances";

            list pcp-igd-iwf-instance {
                key "id";

                description
                 "UPnP IGD/PCP Interworking Function instance";

               leaf id {
                  type uint32;
                  description
                     "An identifier of the IWF instance.";
               }

               leaf name {
                  type string;
                  description
                    "A name of the UPnP IGD-PCP IWF instance";
               }

               list version {
                  key version;
                  description
                    "configures one or several PCP versions.";

                  uses pcp:pcp-version;
               }

               list pcp-servers {
                  key "pcp-server-id";
                  description
                    "List of configured PCP servers.";
                  uses pcp:pcp-server-address;
               }

               leaf authentication-enable {
                  type boolean;
                  description
                   "Enable/disable PCP authentication";
               }

               container igd-version {
                  description
                   "Configure UPnP IGD version(s).";

                  uses igd-version;
               }

               container mapping-table {
                    description
                        "Mapping table as maintained by a
                          UPnP IGD-PCP IWF instance";

                    list mapping-entry {
                      key "index";
                      description
                        "PCP Mapping Entry.";

                    leaf igd-control-point-address {
                        type inet:ip-address;
                        description
                          "IP address of the UPnP Control Point.";
                    }

                    leaf igd-control-point-port {
                        type inet:port-number;
                        description
                         "Port number";
                    }
                    uses pcp:mapping-entry;
                    }
                }
            }
       }
    }

/*
 * PCP state
 */

    container pcp-iwf-state {

        config false;

        description
           "UPnP IGD/PCP Interworking Function";

        container pcp-igd-iwf-instances {
            description
               "UPnP IGD/PCP Interworking Function instances";

            list pcp-igd-iwf-instance {

                key "id";
                description
                    "UPnP IGD/PCP Interworking Function instance";

                leaf id {
                    type int32;
                    description
                        "the identifier of the instance";
                }

                leaf name {
                    type string;
                    description
                     "the name of the instance";
                }

               list supported-version {
                  key version;
                  description
                   "list of supported PCP versions.";

                  uses pcp:pcp-version;
               }

               leaf preferred-version {
                  type uint8;
                  description
                   "Preferred version";
               }

         list pcp-igd-iwf-ip-address {

         key address-id;

           description
             "local IP addresses of the UPnP IGD-PCP IWF";

         leaf address-id {
              type uint32;
              description
                "An identifier of the address";
           }

         leaf ip-address {
              type inet:ipv6-address;
              description
                "An address of the UPnP IGD-PCP IWF";
           }
         }

                leaf authentication-support {
                    type boolean;
                    description
                     "Indicates whether PCP authentication is
                       supported.";
                }

                leaf authentication-enabled{
                    type boolean;
                    description
                      "Indicates whether PCP authentication
                        is enabled.";
                }

                container igd-version-capability {
                   description
                    "List of supported UPnP IGD versions.";

                   uses igd-version;
                }

                container enabled-igd-version {
                   description
                     "Configured UPnP IGD versions";

                   uses igd-version;
                }

               list pcp-server-address {
                  key "pcp-server-id";
                  description
                   "List of provisioned PCP servers";

                  uses pcp:pcp-server-address-status;
               }

           container mapping-table {
                description
                    "PCP Mapping table";

                list mapping-entry {
                    key "index";
                    description
                        "PCP mapping entry.";

                    uses pcp:mapping-entry;
                    uses pcp:status-code;

                    leaf igd-control-point-address {
                        type inet:ip-address;
                        description
                         "The IP address of a UPnP Control Point";
                    }

                    leaf igd-control-point-port {
                        type inet:port-number;
                        description
                         "The port number of a UPnP Control Point";
                    }
               }
           }

           container traffic-statistics {

                description
                    "traffic statistics";

                uses pcp:traffic-stat;

                container mapping-table {
                    description
                        "Mapping table related statistics";

                    uses pcp:mapping-table-stats;
               }
           }
        }
    }
  }
}
