module ietf-te-mpls {

  namespace "urn:ietf:params:xml:ns:yang:ietf-te-mpls";

  /* Replace with IANA when assigned */
  prefix "te-mpls";

  /* Import TE generic types */
  import ietf-te {
    prefix te;
  }

  /* Import TE generic types */
  import ietf-te-types {
    prefix te-types;
  }

  import ietf-routing-types {
    prefix "rt-types";
  }

  import ietf-mpls-static {
    prefix mpls-static;
  }

  import ietf-inet-types {
    prefix inet;
  }

  organization
    "IETF Traffic Engineering Architecture and Signaling (TEAS)
     Working Group";

  contact
    "WG Web:   <http://tools.ietf.org/wg/teas/>
     WG List:  <mailto:teas@ietf.org>

     WG Chair: Lou Berger
               <mailto:lberger@labn.net>

     WG Chair: Vishnu Pavan Beeram
               <mailto:vbeeram@juniper.net>

     Editor:   Tarek Saad
               <mailto:tsaad@cisco.com>

     Editor:   Rakesh Gandhi
               <mailto:rgandhi@cisco.com>

     Editor:   Vishnu Pavan Beeram
               <mailto:vbeeram@juniper.net>

     Editor:   Himanshu Shah
               <mailto:hshah@ciena.com>

     Editor:   Xufeng Liu
               <mailto:xufeng.liu@ericsson.com>

     Editor:   Xia Chen
               <mailto:jescia.chenxia@huawei.com>

     Editor:   Raqib Jones
               <mailto:raqib@Brocade.com>

     Editor:   Bin Wen
               <mailto:Bin_Wen@cable.comcast.com>";

  description
    "YANG data module for MPLS TE configurations,
    state, RPC and notifications.";

  revision "2017-03-10" {
    description "Latest update to MPLS TE YANG module.";
    reference "TBD";
  }

  /* MPLS TE tunnel properties*/

  grouping tunnel-igp-shortcuts {
    description
      "TE tunnel IGP shortcut grouping";
    container tunnel-igp-shortcut {
      description
        "Tunnel IGP shortcut properties";

      leaf shortcut-eligible {
        type boolean;
        default "true";
        description
          "Whether this LSP is considered to be eligible for us as a
           shortcut in the IGP. In the case that this leaf is set to
           true, the IGP SPF calculation uses the metric specified to
           determine whether traffic should be carried over this
           LSP";
      }
      leaf metric-type {
        type identityref {
          base te-types:LSP_METRIC_TYPE;
        }
        default te-types:LSP_METRIC_INHERITED;
        description
          "The type of metric specification that should be used to
           set the LSP(s) metric";
      }
      leaf metric {
        type int32;
        description
          "The value of the metric that should be specified. The
           value supplied in this leaf is used in conjunction with
           the metric type to determine the value of the metric used
           by the system.  Where the metric-type is set to
           LSP_METRIC_ABSOLUTE - the value of this leaf is used
           directly; where it is set to LSP_METRIC_RELATIVE, the
           relevant (positive or negative) offset is used to
           formulate the metric; where metric-type is
           LSP_METRIC_INHERITED, the value of this leaf is not
           utilised";
      }
      leaf-list routing-afs {
        type inet:ip-version;
        description "Address families";
      }
    }
  }

  grouping tunnel-forwarding-adjacency {
    description "Properties for using tunnel in forwarding.";
    container forwarding {
      description
        "Tunnel forwarding properties container";
      
      leaf binding-label {
        type rt-types:mpls-label;
        description "MPLS tunnel binding label";
      }
      leaf load-share {
        type uint32 {
          range "1..4294967295";
        }
        description "ECMP tunnel forwarding load-share factor.";
      }
      leaf policy-class {
        type uint8 {
          range "1..7";
        }
        description
          "The class associated with this tunnel";
      }
    }
  }

  /*** End of MPLS TE tunnel configuration/state */

  /**
   * MPLS TE augmentations
   */

  /* MPLS TE tunnel augmentations */
  augment "/te:te/te:tunnels/te:tunnel" {
    description "MPLS TE tunnel config augmentations";
    uses tunnel-igp-shortcuts;
    uses tunnel-forwarding-adjacency;
  }

  /* MPLS TE LSPs augmentations */
  augment "/te:te/te:tunnels/te:tunnel/" +
          "te:p2p-primary-paths/te:p2p-primary-path" {
    description "MPLS TE LSP augmentation";
    leaf static-lsp-name {
      type mpls-static:static-lsp-ref;
      description "Static LSP name";
    }
  }
  augment "/te:te/te:tunnels/te:tunnel/" +
          "te:p2p-secondary-paths/te:p2p-secondary-path" {
    description "MPLS TE LSP augmentation";
    leaf static-lsp-name {
      type mpls-static:static-lsp-ref;
      description "Static LSP name";
    }
  }
}
