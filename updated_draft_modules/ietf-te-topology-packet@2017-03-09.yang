module ietf-te-topology-packet {
  yang-version 1;
  namespace "urn:ietf:params:xml:ns:yang:ietf-te-topology-packet";

  prefix "tet-pkt";

  import ietf-network {
    prefix "nw";
  }

  import ietf-network-topology {
    prefix "nt";
  }

  import ietf-routing-types {
    prefix "rt-types";
  }

  import ietf-te-topology {
    prefix "tet";
  }

  import ietf-te-types {
    prefix "te-types";
  }

  organization
    "Traffic Engineering Architecture and Signaling (TEAS)
     Working Group";

  contact
    "WG Web:   <http://tools.ietf.org/wg/teas/>
     WG List:  <mailto:teas@ietf.org>

     WG Chair: Lou Berger
               <mailto:lberger@labn.net>

     WG Chair: Vishnu Pavan Beeram
               <mailto:vbeeram@juniper.net>

     Editors:  Xufeng Liu
               <mailto:Xufeng_Liu@jabil.com>

               Igor Bryskin
               <mailto:Igor.Bryskin@huawei.com>

               Vishnu Pavan Beeram
               <mailto:vbeeram@juniper.net>

               Tarek Saad
               <mailto:tsaad@cisco.com>

               Himanshu Shah
               <mailto:hshah@ciena.com>

               Oscar Gonzalez De Dios
               <mailto:oscar.gonzalezdedios@telefonica.com>";

  description "TE topology model";

  revision 2017-03-09 {
    description "Initial revision";
    reference "TBD";
  }

  /*
   * Features
   */

  feature te-performance-metric {
    description
      "This feature indicates that the system supports
       TE performance metric.";
    reference
      "RFC7471: OSPF Traffic Engineering (TE) Metric Extensions.
       RFC7810: IS-IS Traffic Engineering (TE) Metric Extensions.
       RFC7823: Performance-Based Path Selection for Explicitly
       Routed Label Switched Paths (LSPs) Using TE Metric
       Extensions";
  }

  /*
   * Groupings
   */
  grouping packet-switch-capable-container {
    description
      "The container of packet switch capable attributes.";
    container packet-switch-capable {
      description
        "Interface has packet-switching capabilities.";
      leaf minimum-lsp-bandwidth {
        type rt-types:bandwidth-ieee-float32;
        description
          "Minimum LSP Bandwidth. Units in bytes per second";
      }
      leaf interface-mtu {
        type uint16;
        description
          "Interface MTU.";
      }
    }
  }

  /*
   * Augmentations
   */
  /* Augmentations to connectivity-matrix */
  augment "/nw:networks/nw:network/nw:node/tet:te/"
    + "tet:te-node-attributes/tet:connectivity-matrices" {
    description
      "Parameters for PSC TE topology.";
    uses te-types:performance-metric-container {
      if-feature te-performance-metric;
    }
  }

  augment "/nw:networks/nw:network/nw:node/tet:te/"
        + "tet:te-node-attributes/tet:connectivity-matrices/"
        + "tet:connectivity-matrix" {
    description
      "Parameters for PSC TE topology.";
    uses te-types:performance-metric-container {
      if-feature te-performance-metric;
    }
  }

  augment "/nw:networks/nw:network/nw:node/tet:te/"
        + "tet:te-node-attributes/tet:connectivity-matrices" {
    description
      "Parameters for PSC TE topology.";
    uses te-types:performance-metric-container {
      if-feature te-performance-metric;
    }
  }

  augment "/nw:networks/nw:network/nw:node/tet:te/"
        + "tet:te-node-attributes/tet:connectivity-matrices/"
        + "tet:connectivity-matrix" {
    description
      "Parameters for PSC TE topology.";
    uses te-types:performance-metric-container {
      if-feature te-performance-metric;
    }
  }

  augment "/nw:networks/nw:network/nw:node/tet:te/"
        + "tet:information-source-entry/tet:connectivity-matrices" {
    description
      "Parameters for PSC TE topology.";
    uses te-types:performance-metric-container {
      if-feature te-performance-metric;
    }
  }

  augment "/nw:networks/nw:network/nw:node/tet:te/"
        + "tet:information-source-entry/tet:connectivity-matrices/"
        + "tet:connectivity-matrix" {
    description
      "Parameters for PSC TE topology.";
    uses te-types:performance-metric-container {
      if-feature te-performance-metric;
    }
  }

  /* Augmentations to tunnel-termination-point */
  augment "/nw:networks/nw:network/nw:node/tet:te/"
        + "tet:tunnel-termination-point/"
        + "tet:local-link-connectivities" {
    description
      "Parameters for PSC TE topology.";
    uses te-types:performance-metric-container {
      if-feature te-performance-metric;
    }
  }

  augment "/nw:networks/nw:network/nw:node/tet:te/"
        + "tet:tunnel-termination-point/"
        + "tet:local-link-connectivities/"
        + "tet:local-link-connectivity" {
    description
      "Parameters for PSC TE topology.";
    uses te-types:performance-metric-container {
      if-feature te-performance-metric;
    }
  }

  augment "/nw:networks/nw:network/nw:node/tet:te/"
        + "tet:tunnel-termination-point/"
        + "tet:local-link-connectivities" {
    description
      "Parameters for PSC TE topology.";
    uses te-types:performance-metric-container {
      if-feature te-performance-metric;
    }
  }

  /* Augmentations to te-link-attributes */
  augment "/nw:networks/tet:te/tet:templates/"
        + "tet:link-template/tet:te-link-attributes" {
    when "tet:interface-switching-capability "
      + "[tet:switching-capability = 'switching-psc1']" {
      description "Valid only for PSC";
    }
    description
      "Parameters for PSC TE topology.";
    uses te-types:performance-metric-container {
      if-feature te-performance-metric;
    }
  }

  augment "/nw:networks/nw:network/nt:link/tet:te/"
        + "tet:te-link-attributes" {
    when "tet:interface-switching-capability "
      + "[tet:switching-capability = 'switching-psc1']" {
      description "Valid only for PSC";
    }
    description
      "Parameters for PSC TE topology.";
    uses te-types:performance-metric-container {
      if-feature te-performance-metric;
    }
  }

  augment "/nw:networks/nw:network/nt:link/tet:te/"
        + "tet:information-source-entry" {
    when "tet:interface-switching-capability "
      + "[tet:switching-capability = 'switching-psc1']" {
      description "Valid only for PSC";
    }
    description
      "Parameters for PSC TE topology.";
    uses te-types:performance-metric-container {
      if-feature te-performance-metric;
    }
  }

  /* Augmentations to interface-switching-capability */
  augment "/nw:networks/tet:te/tet:templates/"
        + "tet:link-template/tet:te-link-attributes/"
        + "tet:interface-switching-capability" {
    when "tet:switching-capability = 'switching-psc1' " {
      description "Valid only for PSC";
    }
    description
      "Parameters for PSC TE topology.";
    uses packet-switch-capable-container;
  }

  augment "/nw:networks/nw:network/nt:link/tet:te/"
        + "tet:te-link-attributes/"
        + "tet:interface-switching-capability" {
    when "tet:switching-capability = 'switching-psc1' " {
      description "Valid only for PSC";
    }
    description
      "Parameters for PSC TE topology.";
    uses packet-switch-capable-container;
  }

  augment "/nw:networks/nw:network/nt:link/tet:te/"
        + "tet:information-source-entry/"
        + "tet:interface-switching-capability" {
    when "tet:switching-capability = 'switching-psc1' " {
      description "Valid only for PSC";
    }
    description
      "Parameters for PSC TE topology.";
    uses packet-switch-capable-container;
  }
}
