submodule ietf-ipv6-router-advertisements {
  yang-version "1.1";

  belongs-to ietf-ipv6-unicast-routing {
    prefix "v6ur";
  }

  import ietf-inet-types {
    prefix "inet";
  }
  import ietf-interfaces {
    prefix "if";
  }
  import ietf-ip {
    prefix "ip";
  }

  organization
    "IETF NETMOD (NETCONF Data Modeling Language) Working Group";
  contact
    "WG Web:   <https://datatracker.ietf.org/wg/netmod/>
     WG List:  <mailto:netmod@ietf.org>
     
     WG Chair: Lou Berger
               <mailto:lberger@labn.net>
     
     WG Chair: Kent Watsen
               <mailto:kwatsen@juniper.net>
     
     Editor:   Ladislav Lhotka
               <mailto:lhotka@nic.cz>
     
     Editor:   Acee Lindem
               <mailto:acee@cisco.com>";
  description
    "This YANG module augments the 'ietf-ip' module with
     configuration and state data of IPv6 router advertisements.
     
     Copyright (c) 2016 IETF Trust and the persons identified as
     authors of the code.  All rights reserved.
     
     Redistribution and use in source and binary forms, with or
     without modification, is permitted pursuant to, and subject to
     the license terms contained in, the Simplified BSD License set
     forth in Section 4.c of the IETF Trust's Legal Provisions
     Relating to IETF Documents
     (http://trustee.ietf.org/license-info).
     
     The key words 'MUST', 'MUST NOT', 'REQUIRED', 'SHALL', 'SHALL
     NOT', 'SHOULD', 'SHOULD NOT', 'RECOMMENDED', 'MAY', and
     'OPTIONAL' in the module text are to be interpreted as described
     in RFC 2119.
     
     This version of this YANG module is part of RFC 8022;
     see the RFC itself for full legal notices.";
  reference
    "RFC 4861: Neighbor Discovery for IP version 6 (IPv6).";

  revision 2017-04-01 {
    description
      "Restructured to conform to the Network Management Datastore
       Architecture.";
    reference
      "RFC XXX: A YANG Data Model for Routing Management";
  }

  revision 2016-11-04 {
    description
      "Initial revision.";
    reference
      "RFC 8022: A YANG Data Model for Routing Management";
  }

  /* State data */

  augment "/if:interfaces-state/if:interface/ip:ipv6" {
    status deprecated;
    description
      "Augment interface state data with parameters of IPv6 router
       advertisements.";
    container ipv6-router-advertisements {
      status deprecated;
      description
        "Parameters of IPv6 Router Advertisements.";
      leaf send-advertisements {
        type boolean;
        status deprecated;
        description
          "A flag indicating whether or not the router sends periodic
           Router Advertisements and responds to Router
           Solicitations.";
      }
      leaf max-rtr-adv-interval {
        type uint16 {
          range "4..1800";
        }
        units "seconds";
        status deprecated;
        description
          "The maximum time allowed between sending unsolicited
           multicast Router Advertisements from the interface.";
      }
      leaf min-rtr-adv-interval {
        type uint16 {
          range "3..1350";
        }
        units "seconds";
        status deprecated;
        description
          "The minimum time allowed between sending unsolicited
           multicast Router Advertisements from the interface.";
      }
      leaf managed-flag {
        type boolean;
        status deprecated;
        description
          "The value that is placed in the 'Managed address
           configuration' flag field in the Router Advertisement.";
      }
      leaf other-config-flag {
        type boolean;
        status deprecated;
        description
          "The value that is placed in the 'Other configuration' flag
           field in the Router Advertisement.";
      }
      leaf link-mtu {
        type uint32;
        status deprecated;
        description
          "The value that is placed in MTU options sent by the
           router.  A value of zero indicates that no MTU options are
           sent.";
      }
      leaf reachable-time {
        type uint32 {
          range "0..3600000";
        }
        units "milliseconds";
        status deprecated;
        description
          "The value that is placed in the Reachable Time field in
           the Router Advertisement messages sent by the router.  A
           value of zero means unspecified (by this router).";
      }
      leaf retrans-timer {
        type uint32;
        units "milliseconds";
        status deprecated;
        description
          "The value that is placed in the Retrans Timer field in the
           Router Advertisement messages sent by the router.  A value
           of zero means unspecified (by this router).";
      }
      leaf cur-hop-limit {
        type uint8;
        status deprecated;
        description
          "The value that is placed in the Cur Hop Limit field in the
           Router Advertisement messages sent by the router.  A value
           of zero means unspecified (by this router).";
      }
      leaf default-lifetime {
        type uint16 {
          range "0..9000";
        }
        units "seconds";
        status deprecated;
        description
          "The value that is placed in the Router Lifetime field of
           Router Advertisements sent from the interface, in seconds.
           A value of zero indicates that the router is not to be
           used as a default router.";
      }
      container prefix-list {
        status deprecated;
        description
          "A list of prefixes that are placed in Prefix Information
           options in Router Advertisement messages sent from the
           interface.
           
           By default, these are all prefixes that the router
           advertises via routing protocols as being on-link for the
           interface from which the advertisement is sent.";
        list prefix {
          key "prefix-spec";
          status deprecated;
          description
            "Advertised prefix entry and its parameters.";
          leaf prefix-spec {
            type inet:ipv6-prefix;
            status deprecated;
            description
              "IPv6 address prefix.";
          }
          leaf valid-lifetime {
            type uint32;
            units "seconds";
            status deprecated;
            description
              "The value that is placed in the Valid Lifetime in the
               Prefix Information option.  The designated value of
               all 1's (0xffffffff) represents infinity.
               
               An implementation SHOULD keep this value constant in
               consecutive advertisements except when it is
               explicitly changed in configuration.";
          }
          leaf on-link-flag {
            type boolean;
            status deprecated;
            description
              "The value that is placed in the on-link flag ('L-bit')
               field in the Prefix Information option.";
          }
          leaf preferred-lifetime {
            type uint32;
            units "seconds";
            status deprecated;
            description
              "The value that is placed in the Preferred Lifetime in
               the Prefix Information option, in seconds.  The
               designated value of all 1's (0xffffffff) represents
               infinity.
               
               An implementation SHOULD keep this value constant in
               consecutive advertisements except when it is
               explicitly changed in configuration.";
          }
          leaf autonomous-flag {
            type boolean;
            status deprecated;
            description
              "The value that is placed in the Autonomous Flag field
               in the Prefix Information option.";
          }
        }
      }
    }
  }

  /* Configuration data */

  augment "/if:interfaces/if:interface/ip:ipv6" {
    description
      "Augment interfaces with parameters of IPv6 router
       advertisements.";
    container ipv6-router-advertisements {
      description
        "Parameters of IPv6 Router Advertisements.";
      leaf send-advertisements {
        type boolean;
        default "false";
        description
          "A flag indicating whether or not the router sends periodic
           Router Advertisements and responds to Router
           Solicitations.";
        reference
          "RFC 4861: Neighbor Discovery for IP version 6 (IPv6) -
           AdvSendAdvertisements.";
      }
      leaf max-rtr-adv-interval {
        type uint16 {
          range "4..1800";
        }
        units "seconds";
        default "600";
        description
          "The maximum time allowed between sending unsolicited
           multicast Router Advertisements from the interface.";
        reference
          "RFC 4861: Neighbor Discovery for IP version 6 (IPv6) -
           MaxRtrAdvInterval.";
      }
      leaf min-rtr-adv-interval {
        type uint16 {
          range "3..1350";
        }
        units "seconds";
        must ". <= 0.75 * ../max-rtr-adv-interval" {
          description
            "The value MUST NOT be greater than 75% of
             'max-rtr-adv-interval'.";
        }
        description
          "The minimum time allowed between sending unsolicited
           multicast Router Advertisements from the interface.
           
           The default value to be used operationally if this leaf is
           not configured is determined as follows:
           
           - if max-rtr-adv-interval >= 9 seconds, the default
             value is 0.33 * max-rtr-adv-interval;
           
           - otherwise, it is 0.75 * max-rtr-adv-interval.";
        reference
          "RFC 4861: Neighbor Discovery for IP version 6 (IPv6) -
           MinRtrAdvInterval.";
      }
      leaf managed-flag {
        type boolean;
        default "false";
        description
          "The value that is placed in the 'Managed address
           configuration' flag field in the Router Advertisement.";
        reference
          "RFC 4861: Neighbor Discovery for IP version 6 (IPv6) -
           AdvManagedFlag.";
      }
      leaf other-config-flag {
        type boolean;
        default "false";
        description
          "The value that is placed in the 'Other configuration' flag
           field in the Router Advertisement.";
        reference
          "RFC 4861: Neighbor Discovery for IP version 6 (IPv6) -
           AdvOtherConfigFlag.";
      }
      leaf link-mtu {
        type uint32;
        default "0";
        description
          "The value that is placed in MTU options sent by the
           router.  A value of zero indicates that no MTU options are
           sent.";
        reference
          "RFC 4861: Neighbor Discovery for IP version 6 (IPv6) -
           AdvLinkMTU.";
      }
      leaf reachable-time {
        type uint32 {
          range "0..3600000";
        }
        units "milliseconds";
        default "0";
        description
          "The value that is placed in the Reachable Time field in
           the Router Advertisement messages sent by the router.  A
           value of zero means unspecified (by this router).";
        reference
          "RFC 4861: Neighbor Discovery for IP version 6 (IPv6) -
           AdvReachableTime.";
      }
      leaf retrans-timer {
        type uint32;
        units "milliseconds";
        default "0";
        description
          "The value that is placed in the Retrans Timer field in the
           Router Advertisement messages sent by the router.  A value
           of zero means unspecified (by this router).";
        reference
          "RFC 4861: Neighbor Discovery for IP version 6 (IPv6) -
           AdvRetransTimer.";
      }
      leaf cur-hop-limit {
        type uint8;
        description
          "The value that is placed in the Cur Hop Limit field in the
           Router Advertisement messages sent by the router.  A value
           of zero means unspecified (by this router).
           
           If this parameter is not configured, the device SHOULD use
           the value specified in IANA Assigned Numbers that was in
           effect at the time of implementation.";
        reference
          "RFC 4861: Neighbor Discovery for IP version 6 (IPv6) -
           AdvCurHopLimit.
           
           IANA: IP Parameters,
           http://www.iana.org/assignments/ip-parameters";
      }
      leaf default-lifetime {
        type uint16 {
          range "0..9000";
        }
        units "seconds";
        description
          "The value that is placed in the Router Lifetime field of
           Router Advertisements sent from the interface, in 
           seconds.  A value of zero indicates that the router is
           not to be used as a default router.

           If configured, the value MUST be either zero or between
           max-rtr-adv-interval and 9000 seconds. 

           These limits may be overridden by specific documents that
           describe how IPv6 operates over different link layers.
           
           If this parameter is not configured, the device SHOULD use
           a value of 3 * max-rtr-adv-interval.";
        reference
          "RFC 4861: Neighbor Discovery for IP version 6 (IPv6) -
           AdvDefaultLifeTime.";
      }
      container no-advertise-prefix-list {
        description
          "Configuration of prefixes to be placed in Prefix
           Information options in Router Advertisement messages sent
           from the interface.
           
           Prefixes that are advertised by default but do not have
           their entries in the child 'prefix' list are advertised
           with the default values of all parameters.
           
           The link-local prefix SHOULD NOT be included in the list
           of advertised prefixes.
           
           FROM STATE TREE (FIX ME):
           A list of prefixes that are placed in Prefix Information
           options in Router Advertisement messages sent from the
           interface.
           
           By default, these are all prefixes that the router
           advertises via routing protocols as being on-link for the
           interface from which the advertisement is sent.";
        reference
          "RFC 4861: Neighbor Discovery for IP version 6 (IPv6) -
           AdvPrefixList.";
        list prefix {
          key "prefix-spec";
          description
            "Configuration of an advertised prefix entry.
             
             FROM STATE TREE (FIX ME):
             Advertised prefix entry and its parameters.";
          leaf prefix-spec {
            type inet:ipv6-prefix;
            description
              "IPv6 address prefix.";
          }
          choice control-adv-prefixes {
            default "advertise";
            description
              "Either the prefix is explicitly removed from the
               set of advertised prefixes, or the parameters with
               which it is advertised are specified (default case).";
            leaf no-advertise {
              type empty;
              description
                "The prefix will not be advertised.
                 
                 This can be used for removing the prefix from the
                 default set of advertised prefixes.";
            }
          }
        }
      }
      container prefix-list {
        // TODO - This description needs to be checked carefully to
        // ensure that it is still correct.        
        description
          "A list of prefixes that are placed in Prefix Information
           options in Router Advertisement messages sent from the
           interface.
           
           By default, these are all prefixes that the router
           advertises via routing protocols as being on-link for the
           interface from which the advertisement is sent.

           TODO - this this right:
           The link-local prefix SHOULD NOT be included in the list
           of advertised prefixes.";
        reference
          "RFC 4861: Neighbor Discovery for IP version 6 (IPv6) -
           AdvPrefixList.";
        list prefix {
          key "prefix-spec";
          description
            "Configuration of an advertised prefix entry.
             
             FROM STATE TREE (FIX ME):
             Advertised prefix entry and its parameters.";
          leaf prefix-spec {
            type inet:ipv6-prefix;
            description
              "IPv6 address prefix.";
          }
          leaf valid-lifetime {
            type uint32;
            units "seconds";
            config false;
            description
              "The value that is placed in the Valid Lifetime in the
               Prefix Information option.  The designated value of
               all 1's (0xffffffff) represents infinity.
               
               An implementation SHOULD keep this value constant in
               consecutive advertisements except when it is
               explicitly changed in configuration.";
          }
          leaf on-link-flag {
            type boolean;
            config false;
            description
              "The value that is placed in the on-link flag ('L-bit')
               field in the Prefix Information option.";
          }
          leaf preferred-lifetime {
            type uint32;
            units "seconds";
            config false;
            description
              "The value that is placed in the Preferred Lifetime in
               the Prefix Information option, in seconds.  The
               designated value of all 1's (0xffffffff) represents
               infinity.
               
               An implementation SHOULD keep this value constant in
               consecutive advertisements except when it is
               explicitly changed in configuration.";
          }
          leaf autonomous-flag {
            type boolean;
            config false;
            description
              "The value that is placed in the Autonomous Flag field
               in the Prefix Information option.";
          }
        }
      }
    }
  }
}
